# DIN VDE 0132 (VDE 0132):2018-07

# Specification: DIN VDE 0132 (VDE 0132):2018-07
- bib.dp.publication-date: 2018-06-29
- bib.tg.title-german: Brandbekämpfung und technische Hilfeleistung im Bereich elektrischer Anlagen
- ids.document: 7104561
- pub.software: VDE CaaS 0.1.6
- pub.supplier: VDE
- pub.transformation-date: 2025-09-16T09:26:02.399708915Z

## pkn--7104561: Brandbekämpfung und technische Hilfeleistung im Bereich elektrischer Anlagen (document)
DIN VDE 0132 (VDE 0132):2018-07
- bib.al.original-language: en
- bib.dp.publication-date: 2018-06-29
- bib.ts.document-type: WN
- ids.document: 7104561
- obj.language: de
- obj.specobject-type: document
- pub.harmonization: IDiS ReqIF interpretation for public standards 1.3
- pub.sales-number: 0100473
- pub.software: VDE CaaS 0.1.6
- pub.supplier: VDE
- pub.transformation-date: 2025-09-16T09:26:02.399708915Z
- pub.url: https://[changeme].dke.de/api/publications/7104561/reqif

## R2 (heading)
- bib.al.original-language: en
- bib.dp.publication-date: 2018-06-29
- ids.document: 7104561
- obj.element-name: heading
- obj.language: de
- obj.specobject-type: heading

### tr--8e9b9d1a-8157-4b81-a49d-2d500c597b66--HwkJAaNbewPb (provision)
|  |  |  | DIN VDE 0132 (VDE 0132) |  |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 |  |  |
| --- | --- | --- | --- | --- | --- | --- | --- |
|  |  |  | Diese Norm ist zugleich eine VDE-Bestimmung im Sinne von VDE 0022. Sie ist nach Durchführung des vom VDE-Präsidium beschlossenen Genehmigungsverfahrens unter der oben angeführten Nummer in das VDE-Vorschriftenwerk aufgenommen und in der „etz Elektrotechnik + Automation“ bekannt gegeben worden. |  |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 |  |  |
| Vervielfältigung – auch für innerbetriebliche Zwecke – nicht gestattet. |  |  |  |  |  |  |  |
|  |  | ICS 13.220.10 |  | Ersatz für DIN VDE 0132 (VDE 0132):2015-10 Siehe Anwendungsbeginn |  |  |  |
|  | Brandbekämpfung und technische Hilfeleistung im Bereich elektrischer Anlagen Firefighting and technical assistance in or near electrical installations Lutte contre l’incendie et secours technique dans ou prés des installations électriques |  |  |  |  |  |  |
|  | Gesamtumfang 28 Seiten DKE Deutsche Kommission Elektrotechnik Elektronik Informationstechnik in DIN und VDE |  |  |  |  |  |  |
| © DIN Deutsches Institut für Normung e. V. und VDE Verband der Elektrotechnik Elektronik Informationstechnik e. V. Jede Art der Vervielfältigung, auch auszugsweise, nur mit Genehmigung des DIN, Berlin, und des VDE, Frankfurt am Main, gestattet. Einzelverkauf und Abonnements durch VDE VERLAG GMBH, 10625 Berlin Einzelverkauf auch durch Beuth Verlag GmbH, 10772 Berlin |  |  |  |  |  | Preisgr. 19 K VDE-Vertr.-Nr. 0100473 |  |
- bib.al.original-language: en
- bib.dp.publication-date: 2018-06-29
- ids.document: 7104561
- ids.tracing: hash-cacb19240bc41ceb9f7bcbe15b97f0b9ba7b664e3d9e003de4b1c988d2c954b0
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

## R4: Anwendungsbeginn (heading)
- bib.al.original-language: en
- bib.dp.publication-date: 2018-06-29
- ids.document: 7104561
- obj.element-name: heading
- obj.language: de
- obj.specobject-type: heading

### tr--hash-01840b81e195e890e6ae486e65b2769e60ad92b47a7f49ec4309436ab3e3c97b--k5i3VnVGpZPc: Anwendungsbeginn (provision)
Anwendungsbeginn dieser Norm ist 2018-07-01.
- bib.al.original-language: en
- bib.dp.publication-date: 2018-06-29
- ids.document: 7104561
- ids.tracing: hash-01840b81e195e890e6ae486e65b2769e60ad92b47a7f49ec4309436ab3e3c97b
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--hash-9721f9a268a99da63941d64619d4bb67ee877740bbe619fc7859204600d3a2cc--BBznxLLCybxa: Anwendungsbeginn (provision)
Für DIN VDE 0132 (VDE 0132):2015-10 besteht eine Übergangsfrist bis 2021-06-30.
- bib.al.original-language: en
- bib.dp.publication-date: 2018-06-29
- ids.document: 7104561
- ids.tracing: hash-9721f9a268a99da63941d64619d4bb67ee877740bbe619fc7859204600d3a2cc
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

## R7: Vorwort (heading)
- bib.al.original-language: en
- bib.dp.publication-date: 2018-06-29
- ids.document: 7104561
- obj.element-name: heading
- obj.language: de
- obj.specobject-type: heading

### tr--hash-b6ff58cf5255db062f634deef93c96a64a8a474ea0a17a8f610dad53408fdf24--TVmek3g6Vf1L: Vorwort (provision)
Vorausgegangener Norm-Entwurf: E DIN VDE 0132 (VDE 0132):2017-04.
- bib.al.original-language: en
- bib.dp.publication-date: 2018-06-29
- ids.document: 7104561
- ids.tracing: hash-b6ff58cf5255db062f634deef93c96a64a8a474ea0a17a8f610dad53408fdf24
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--hash-0275a7de5e261ad7dd5d1eaf0832b228b8448540d29ec6fd0e377ed3a8464c4e--mDUpa1QMhVKQ: Vorwort (provision)
Für diese Norm ist das nationale Arbeitsgremium K 213 „Brandbekämpfung in elektrischen Anlagen“ der DKE Deutsche Kommission Elektrotechnik Elektronik Informationstechnik in DIN und VDE (www.dke.de) zuständig.
- bib.al.original-language: en
- bib.dp.publication-date: 2018-06-29
- ids.document: 7104561
- ids.tracing: hash-0275a7de5e261ad7dd5d1eaf0832b228b8448540d29ec6fd0e377ed3a8464c4e
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--hash-68da47c471bff1fcc039c0d1d59ba8f6ed1983e35cd853a74b67e8528de4b76c--Q5os005U6peO: Vorwort (provision)
Diese Norm regelt das Verhalten und die Verwendung von Geräten für die Brandbekämpfung und technische Hilfeleistung in elektrischen Anlagen und in deren Nähe.
- bib.al.original-language: en
- bib.dp.publication-date: 2018-06-29
- ids.document: 7104561
- ids.tracing: hash-68da47c471bff1fcc039c0d1d59ba8f6ed1983e35cd853a74b67e8528de4b76c
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--hash-b17a358f6c75a27a74e78ab8e66461e70f12f5284b6ab72c9f310233c8cae2b7--9GOgzFt2espP: Vorwort (provision)
Zudem kann diese Norm dem Anwender Hilfestellung bei der Erstellung der Gefährdungsbeurteilung nach der Betriebsicherheitsverordnung bzw. der DGUV Vorschrift 1 „Grundsätze der Prävention“ geben.
- bib.al.original-language: en
- bib.dp.publication-date: 2018-06-29
- ids.document: 7104561
- ids.tracing: hash-b17a358f6c75a27a74e78ab8e66461e70f12f5284b6ab72c9f310233c8cae2b7
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### R12: Es wird auf die Möglichkeit hingewiesen, dass einige Elemente dieses Dokuments Patentrechte berühren können. DIN und DKE sind nicht dafür verantwortlich, einige oder alle diesbezüglichen Patentrechte zu identifizieren. (heading)
- bib.al.original-language: en
- bib.dp.publication-date: 2018-06-29
- ids.document: 7104561
- obj.clause-number: Es wird auf die Möglichkeit hingewiesen, dass einige Elemente di
- obj.element-name: heading
- obj.language: de
- obj.specobject-type: heading
- obj.transformation-issues: Exceeded string length (ATTRIBUTE-DEFINITION-STRING: "tr--ads--heading--obj.clause-number", VALUE original: "Es wird auf die Möglichkeit hingewiesen, dass einige Elemente dieses Dokuments Patentrechte berühren können. DIN und DKE sind nicht dafür verantwortlich, einige oder alle diesbezüglichen Patentrechte zu identifizieren.", VALUE truncated: "Es wird auf die Möglichkeit hingewiesen, dass einige Elemente di")

### R13: Änderungen (heading)
- bib.al.original-language: en
- bib.dp.publication-date: 2018-06-29
- ids.document: 7104561
- obj.element-name: heading
- obj.language: de
- obj.specobject-type: heading

#### tr--hash-c53905c0cd708955a879212fc0c87fd104a30f925c7b1d69c97152cdefa72166--vAYorTnv4GAb: Änderungen (provision)
Gegenüber DIN VDE 0132 (VDE 0132):2015-10 wurden folgende Änderungen vorgenommen:
- a) 5.1.3 "Maßnahmen bei Überflutung zur Sicherstellung der Personensicherheit" redaktionell geändert;
- b) 5.1.5 "Besondere Maßnahmen bei Lithium-Ionen-Akkumulatoren" neu aufgenommen.
- bib.al.original-language: en
- bib.dp.publication-date: 2018-06-29
- ids.document: 7104561
- ids.tracing: hash-c53905c0cd708955a879212fc0c87fd104a30f925c7b1d69c97152cdefa72166
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R129
- cross-reference -> R153

### R15: Frühere Ausgaben (heading)
- bib.al.original-language: en
- bib.dp.publication-date: 2018-06-29
- ids.document: 7104561
- obj.element-name: heading
- obj.language: de
- obj.specobject-type: heading

#### tr--hash-e9ba8679aeb384f67e014e4d24bbf4cf58e227931681cbe6ca20e7e85de0d632--jooeJDJmcCW4: Frühere Ausgaben (provision)
DIN VDE 0132 (VDE 0132): 1979-02, 1989-11 , 2001-08 , 2008-08 , 2012-08 , 2015-10
- bib.al.original-language: en
- bib.dp.publication-date: 2018-06-29
- ids.document: 7104561
- ids.tracing: hash-e9ba8679aeb384f67e014e4d24bbf4cf58e227931681cbe6ca20e7e85de0d632
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

## R17: Anwendungsbereich (heading)
- bib.al.original-language: en
- bib.dp.publication-date: 2018-06-29
- ids.document: 7104561
- obj.clause-number: 1
- obj.element-name: heading
- obj.language: de
- obj.specobject-type: heading
- ChapterName: 1 Anwendungsbereich

### tr--hash-3b013f996659abdca99495c91d5d6f407077d95214c03c12bfeab0a6e8639d35--G7tmwkBAKnZL: Anwendungsbereich (provision)
Diese Norm dient zur Unterrichtung der Personen, die für die Brandbekämpfung und technische Hilfeleistung in elektrischen Anlagen und in deren Nähe zuständig sind.
- bib.al.original-language: en
- bib.dp.publication-date: 2018-06-29
- ids.document: 7104561
- ids.tracing: hash-3b013f996659abdca99495c91d5d6f407077d95214c03c12bfeab0a6e8639d35
- obj.clause-number: 1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--hash-a39c2f346027ca6b42a234d54a988556cf461077ca63f44b28a8d53c09e9c688--gOsK3wF2DfWf: Anwendungsbereich (provision)
Die in dieser Norm angegebenen Werte der Mindestabstände für Annäherung und Löschmitteleinsatz gelten nicht für Anlagen mit Nennspannungen bis AC 50 V (Wechselspannung) / DC 120 V (Gleichspannung).
- bib.al.original-language: en
- bib.dp.publication-date: 2018-06-29
- ids.document: 7104561
- ids.tracing: hash-a39c2f346027ca6b42a234d54a988556cf461077ca63f44b28a8d53c09e9c688
- obj.clause-number: 1
- obj.element-name: paragraph
- obj.language: de
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

### tr--hash-2d91564da5f71cd2dd511c537352e01b2e20068a84c56fd25d5eabf5d725a57c--edsyqnuxVlbA: Anwendungsbereich (provision)
Die Norm gilt nicht für die Errichtung und den Betrieb ortsfester Löschanlagen, für Beregnungsanlagen, Wasserwerfer und dergleichen sowie für besondere Löschmaßnahmen, wie z. B. das Fluten von Kabelkanälen mit Wasser oder Schaum.
- bib.al.original-language: en
- bib.dp.publication-date: 2018-06-29
- ids.document: 7104561
- ids.tracing: hash-2d91564da5f71cd2dd511c537352e01b2e20068a84c56fd25d5eabf5d725a57c
- obj.clause-number: 1
- obj.element-name: paragraph
- obj.language: de
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

### tr--hash-5cb469ecd160f8d8c872452bfe6c64fdf18ab4e81ffc383f04a943cc43034381--4VbfjaB3mV5R: Anwendungsbereich (provision)
Diese Norm gilt auch für die Verwendung von Strahlrohren nach DIN 14365-1:1991-02 und DIN 14365-2:1986-09, die nicht europäisch genormt sind, sofern diese noch im Einsatz sind.
- bib.al.original-language: en
- bib.dp.publication-date: 2018-06-29
- ids.document: 7104561
- ids.tracing: hash-5cb469ecd160f8d8c872452bfe6c64fdf18ab4e81ffc383f04a943cc43034381
- obj.clause-number: 1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

## R22: Normative Verweisungen (heading)
- bib.al.original-language: en
- bib.dp.publication-date: 2018-06-29
- ids.document: 7104561
- obj.clause-number: 2
- obj.element-name: heading
- obj.language: de
- obj.specobject-type: heading
- ChapterName: 2 Normative Verweisungen

### tr--hash-19ac98809402cc9d36bbec92e184996209a61abf4b32a1a87220f8f8a849dcff--aaojd8bKz8hv: Normative Verweisungen (provision)
Die folgenden Dokumente, die in diesem Dokument teilweise oder als Ganzes zitiert werden, sind für die Anwendung dieses Dokuments erforderlich.
- bib.al.original-language: en
- bib.dp.publication-date: 2018-06-29
- ids.document: 7104561
- ids.tracing: hash-19ac98809402cc9d36bbec92e184996209a61abf4b32a1a87220f8f8a849dcff
- obj.clause-number: 2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--hash-821db916888fc1f6800c4d901a4e6394caf878587685c36e0bdc19b86b134bb4--OhtlXE6WcnIF: Normative Verweisungen (provision)
Bei datierten Verweisungen gilt nur die in Bezug genommene Ausgabe.
- bib.al.original-language: en
- bib.dp.publication-date: 2018-06-29
- ids.document: 7104561
- ids.tracing: hash-821db916888fc1f6800c4d901a4e6394caf878587685c36e0bdc19b86b134bb4
- obj.clause-number: 2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--hash-27da64891ebe10e3410ffb6958cb8df24bd428763e850ce524b86eb8a7146807--cT5jGcayjFBF: Normative Verweisungen (provision)
Bei undatierten Verweisungen gilt die letzte Ausgabe des in Bezug genommenen Dokuments (einschließlich aller Änderungen).
- DIN 14095, Feuerwehrpläne für bauliche Anlagen ^1)
- DIN 14365-1:1991-02, Mehrzweckstrahlrohre PN 16 – Maße, Werkstoffe, Ausführung, Kennzeichnung
- DIN 14365-2:1986-09, Mehrzweckstrahlrohre PN 16 – Anforderungen, Prüfung^1)
- DIN 14366-2:1984-10, Schaumstrahlrohre für Werfer-Unterteile^1)
- DIN EN 2:2005-01, Brandklassen; Deutsche Fassung EN 2:1992 + A1:2004
- DIN EN 3-7:2007-10, Tragbare Feuerlöscher – Teil 7: Eigenschaften, Leistungsanforderungen und Prüfungen; Deutsche Fassung EN 3-7:2004 + A1:2007
- DIN EN 615:2009-08, Brandschutz – Löschmittel – Anforderungen an Löschpulver (nicht für Löschpulver der Brandklasse D); Deutsche Fassung EN 615:2009
- DIN EN 1568 (alle Teile), Feuerlöschmittel – Schaummittel
- DIN EN 15182-1:2010-04, Strahlrohre für die Brandbekämpfung – Teil 1: Allgemeine Anforderungen; Deutsche Fassung EN 15182-1:2007 + A1:2009
- DIN EN 15182-2:2010-04, Strahlrohre für die Brandbekämpfung – Teil 2: Hohlstrahlrohre PN 16; Deutsche Fassung EN 5182-2:2007 + A1:2009
- DIN EN 15182-3:2010-04, Strahlrohre für die Brandbekämpfung – Teil 3: Strahlrohre mit Vollstrahl und/oder einem unveränderlichen Sprühstrahlwinkel PN 16; Deutsche Fassung EN 15182-3:2007 + A1:2009
- DIN EN 15182-4:2010-04, Strahlrohre für die Brandbekämpfung – Teil 4: Hochdruckstrahlrohre PN 40; Deutsche Fassung EN 15182-4:2007 + A1:2009
- DIN EN 15767-3:2010-12, Tragbare Geräte zum Ausbringen von Löschmitteln, welche mit Feuerlöschpumpen gefördert werden – Tragbare Werfer – Teil 3: Schaumdüsen; Deutsche Fassung EN 15767-3:2010
- DIN EN 16327:2014-07, Feuerwehrwesen – Druckzumischanlagen (DZA) und Druckluftschaumanlagen (DLS); Deutsche Fassung EN 16327:2014
- DIN EN 16712-3:2015-12, Tragbare Geräte zum Ausbringen von Löschmitteln, die mit Feuerlöschpumpen gefördert werden – Tragbare Schaumgeräte – Teil 3: Schwer- und Mittelschaumrohre PN 16; Deutsche Fassung EN°16712-3:2015
- DIN EN 50122-1 (VDE 0115-3):2017-10 , Bahnanwendungen – Ortsfeste Anlagen – Elektrische Sicherheit, Erdung und Rückleitung – Teil 1: Schutzmaßnahmen gegen elektrischen Schlag; Deutsche Fassung EN 50122-1:2011 + A1:2011 + AC:2012 + AC:2016 + A3:2016 + A4:2017
- DIN EN 62040-1 (VDE 0558-510):2013-11 , Unterbrechungsfreie Stromversorgungssysteme (USV) – Teil 1: Allgemeine Anforderungen und Sicherheitsanforderungen (IEC 62040-1:2008 + Corrigendum September 2008 + A1:2013); Deutsche Fassung EN 62040-1:2008 + Corrigendum Februar 2009 + A1:2013
- DIN VDE 0105-100 (VDE 0105-100):2015-10 , Betrieb von elektrischen Anlagen – Teil 100: Allgemeine Festlegungen
- DIN VDE 0105-103 (VDE 0105-103):2014-10 , Betrieb von elektrischen Anlagen – Zusatzfestlegungen für Bahnen
- E DIN IEC 62335 (VDE 0661-20):2008-08, Ortsveränderliche Fehlerstrom-Schutzeinrichtungen mit geschaltetem Schutzleiter zur Anwendung für Geräte der Schutzklasse I und für batteriebetriebene Fahrzeuge (IEC 23E/632/CDV:2007)
- DIN EN ISO 7010, Graphische Symbole – Sicherheitsfarben und Sicherheitszeichen – Registrierte Sicherheitszeichen
- IEC 60417-DB:2010, Graphische Symbole für Betriebsmittel
- Feuerwehrdienstvorschrift 500, Einheiten im ABC-Einsatz ^2)
- DGUV Information 204-006, Anleitung zur Ersten Hilfe ^3)
- DGUV Fachinformation, 2016-09, Stromunfall - Ärztliche Vorstellung notwendig ^3)
- bib.al.original-language: en
- bib.dp.publication-date: 2018-06-29
- ids.document: 7104561
- ids.tracing: hash-27da64891ebe10e3410ffb6958cb8df24bd428763e850ce524b86eb8a7146807
- obj.clause-number: 2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--8e9b9d1a-8157-4b81-a49d-2d500c597b66--aS7nTh3gB7E5: Normative Verweisungen (provision)
1)
Zurückgezogen.
- bib.al.original-language: en
- bib.dp.publication-date: 2018-06-29
- ids.document: 7104561
- ids.tracing: hash-d540af5aa0a2ed12dfce9361af3d8f3f65789242a070ba80490ad196ac8e68ae
- obj.clause-number: 2
- obj.element-name: footnote
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### tr--8e9b9d1a-8157-4b81-a49d-2d500c597b66--SXLwHuN13Urc: Normative Verweisungen (provision)
2)
Zu beziehen bei: Ausschuss Feuerwehrangelegenheiten, Katastrophenschutz und zivile Verteidigung (AFKzV). Diese Dienstvorschrift wurde vom AFKzV den Ländern zur Einführung empfohlen.
- bib.al.original-language: en
- bib.dp.publication-date: 2018-06-29
- ids.document: 7104561
- ids.tracing: hash-2cdc77357e457d7fc52f6e2baf980d21df2c9f6c741fdf4711acfe0f5139c71d
- obj.clause-number: 2
- obj.element-name: footnote
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### tr--8e9b9d1a-8157-4b81-a49d-2d500c597b66--7KupcIsTqXEQ: Normative Verweisungen (provision)
3)
Zu beziehen bei: DGUV Deutsche Gesetzliche Unfallversicherung.
- bib.al.original-language: en
- bib.dp.publication-date: 2018-06-29
- ids.document: 7104561
- ids.tracing: hash-56845993f4bf871301ea3d241ff1195eff9d3cc3f4b6c0a31654e2f90382b5e7
- obj.clause-number: 2
- obj.element-name: footnote
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### tr--8e9b9d1a-8157-4b81-a49d-2d500c597b66--waBk1U0Mj0MI: Normative Verweisungen (provision)
3)
Zu beziehen bei: DGUV Deutsche Gesetzliche Unfallversicherung.
- bib.al.original-language: en
- bib.dp.publication-date: 2018-06-29
- ids.document: 7104561
- ids.tracing: hash-4067c32160e7838bf64b32cf5247d344408c83c0261f71cdda0816462cd3d199
- obj.clause-number: 2
- obj.element-name: footnote
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--hash-484465d16f5b097fb2d625429e3099e7a70b22659ef5ffdf867b6c38a9d848a6--ez5a3Yett4QG: Normative Verweisungen (provision)
Zurückgezogen.
- bib.al.original-language: en
- bib.dp.publication-date: 2018-06-29
- ids.document: 7104561
- ids.tracing: hash-484465d16f5b097fb2d625429e3099e7a70b22659ef5ffdf867b6c38a9d848a6
- obj.clause-number: 2
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--hash-698ded7ac394a092f75417e6c2671031c32a6f303bfee51da06b85f08bef993c--lZmMEqBvgl4x: Normative Verweisungen (provision)
Zu beziehen bei: Ausschuss Feuerwehrangelegenheiten, Katastrophenschutz und zivile Verteidigung (AFKzV).
- bib.al.original-language: en
- bib.dp.publication-date: 2018-06-29
- ids.document: 7104561
- ids.tracing: hash-698ded7ac394a092f75417e6c2671031c32a6f303bfee51da06b85f08bef993c
- obj.clause-number: 2
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--hash-49ab60117a44143df5443fc15f14e244c0aa9ab220ccbd62d4526aa77ce64cfb--vWGjfFAlr86R: Normative Verweisungen (provision)
Diese Dienstvorschrift wurde vom AFKzV den Ländern zur Einführung empfohlen.
- bib.al.original-language: en
- bib.dp.publication-date: 2018-06-29
- ids.document: 7104561
- ids.tracing: hash-49ab60117a44143df5443fc15f14e244c0aa9ab220ccbd62d4526aa77ce64cfb
- obj.clause-number: 2
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--hash-8b9ce7c5fb1747839639224d3a6bd12ae731c4d13cf06cc01dc6916a0ccc139a--aReQJRTwwnpc: Normative Verweisungen (provision)
Zu beziehen bei: DGUV Deutsche Gesetzliche Unfallversicherung.
- bib.al.original-language: en
- bib.dp.publication-date: 2018-06-29
- ids.document: 7104561
- ids.tracing: hash-8b9ce7c5fb1747839639224d3a6bd12ae731c4d13cf06cc01dc6916a0ccc139a
- obj.clause-number: 2
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--hash-8be6767ed1b1b545b63255d1d4904ca6310607e83939336d4ff7b7b27f76c787--KSA32xBZoRdr: Normative Verweisungen (provision)
Zu beziehen bei: DGUV Deutsche Gesetzliche Unfallversicherung.
- bib.al.original-language: en
- bib.dp.publication-date: 2018-06-29
- ids.document: 7104561
- ids.tracing: hash-8be6767ed1b1b545b63255d1d4904ca6310607e83939336d4ff7b7b27f76c787
- obj.clause-number: 2
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

## R35: Begriffe (heading)
- bib.al.original-language: en
- bib.dp.publication-date: 2018-06-29
- ids.document: 7104561
- obj.clause-number: 3
- obj.element-name: heading
- obj.language: de
- obj.specobject-type: heading
- ChapterName: 3 Begriffe

### tr--hash-60c8c0d7ce58af0ce1af9d357a49a2455374241ab686a7c4d44c9875e84ddeeb--V5El1MRLzHwY: Begriffe (provision)
Für die Anwendung dieses Dokuments gelten die folgenden Begriffe.
- bib.al.original-language: en
- bib.dp.publication-date: 2018-06-29
- ids.document: 7104561
- ids.tracing: hash-60c8c0d7ce58af0ce1af9d357a49a2455374241ab686a7c4d44c9875e84ddeeb
- obj.clause-number: 3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--8e9b9d1a-8157-4b81-a49d-2d500c597b66--thVMRptBFZUv: abgeschlossene elektrische Betriebsstätte (provision)
3.1
abgeschlossene elektrische Betriebsstätte
Raum oder ein Ort, der ausschließlich zum Betrieb elektrischer Anlagen dient und unter Verschluss gehalten wird. Zutritt haben Elektrofachkräfte und elektrotechnisch unterwiesene Personen, Laien jedoch nur in Begleitung von Elektrofachkräften oder elektrotechnisch unterwiesenen Personen.
Anmerkung 1 zum Begriff: Hierzu gehören z. B. abgeschlossene Schalt- und Verteilungsanlagen, Transformatorzellen, Schaltfelder, Maststationen.
[QUELLE: DIN VDE 0105-100 (VDE 0105-100):2015-10 ]
- bib.al.original-language: en
- bib.dp.publication-date: 2018-06-29
- ids.document: 7104561
- ids.tracing: hash-5a4c1437a869e3d30c878fcc701cb078bc287ef2a96d436425ff3cfcd6845021
- obj.clause-number: 3.1
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-c0526bf5d72e52f85c79e2ed56a13f1a8981e8130f34fb99260aa1e29f706ad2--RwyGTXXdEoHd: abgeschlossene elektrische Betriebsstätte (provision)
Raum oder ein Ort, der ausschließlich zum Betrieb elektrischer Anlagen dient und unter Verschluss gehalten wird.
- bib.al.original-language: en
- bib.dp.publication-date: 2018-06-29
- ids.document: 7104561
- ids.tracing: hash-c0526bf5d72e52f85c79e2ed56a13f1a8981e8130f34fb99260aa1e29f706ad2
- obj.clause-number: 3.1
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-a7e9e76ca54f51ace17ce7e0c3edbf95d51b612ac1edaf242d81a30a43f8806f--1JA5pinZB06H: abgeschlossene elektrische Betriebsstätte (provision)
Zutritt haben Elektrofachkräfte und elektrotechnisch unterwiesene Personen, Laien jedoch nur in Begleitung von Elektrofachkräften oder elektrotechnisch unterwiesenen Personen.
- bib.al.original-language: en
- bib.dp.publication-date: 2018-06-29
- ids.document: 7104561
- ids.tracing: hash-a7e9e76ca54f51ace17ce7e0c3edbf95d51b612ac1edaf242d81a30a43f8806f
- obj.clause-number: 3.1
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--8e9b9d1a-8157-4b81-a49d-2d500c597b66--iJswLQUzMTF4: Anlagenverantwortlicher (provision)
3.2
Anlagenverantwortlicher
eine Person, die beauftragt ist, während der Durchführung von Arbeiten die unmittelbare Verantwortung für den sicheren Betrieb der elektrischen Anlage zu tragen, die zur Arbeitsstelle gehört
Anmerkung 1 zum Begriff: Der Anlagenverantwortliche hat die möglichen Auswirkungen der Arbeiten auf die elektrische Anlage oder die Teile davon, die in seiner Verantwortung stehen, sowie die Auswirkungen der elektrischen Anlage auf die Arbeitsstelle und die arbeitenden Personen zu beurteilen. Erforderlichenfalls können einige mit dieser Verantwortung einhergehende Verpflichtungen auf andere Personen übertragen werden (siehe auch DIN VDE 0105-100 (VDE 0105-100):2015-10, 4.3 ).
[QUELLE: DIN VDE 0105-100 (VDE 0105-100):2015-10 , modifiziert, Anmerkung 2 wurde nicht übernommen.]
- bib.al.original-language: en
- bib.dp.publication-date: 2018-06-29
- ids.document: 7104561
- ids.tracing: hash-a33fbcd16b973806afe956921336ba27cf869b6ac2febd698df349f79662d1fb
- obj.clause-number: 3.2
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-e213b8d979d0c41d5e1716afede47d8947ec5033b77ef2320b86ac9a61d17efd--dY1v9gv7fjX0: Anlagenverantwortlicher (provision)
eine Person, die beauftragt ist, während der Durchführung von Arbeiten die unmittelbare Verantwortung für den sicheren Betrieb der elektrischen Anlage zu tragen, die zur Arbeitsstelle gehört
- bib.al.original-language: en
- bib.dp.publication-date: 2018-06-29
- ids.document: 7104561
- ids.tracing: hash-e213b8d979d0c41d5e1716afede47d8947ec5033b77ef2320b86ac9a61d17efd
- obj.clause-number: 3.2
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--8e9b9d1a-8157-4b81-a49d-2d500c597b66--X68X5uuHzwU2: Anlagenbetreiber (provision)
3.3
Anlagenbetreiber
Person mit der Gesamtverantwortung für den sicheren Betrieb der elektrischen Anlage, die Regeln und Randbedingungen der Organisation vorgibt
Anmerkung 1 zum Begriff: Diese Person kann der Eigentümer, Unternehmer, Besitzer oder eine beauftragte Person sein, die die Unternehmerpflichten wahrnimmt.
Anmerkung 2 zum Begriff: Erforderlichenfalls können einige mit dieser Verantwortung einhergehende Verpflichtungen auf andere Personen übertragen werden. Bei umfangreichen oder komplexen Anlagen kann diese Zuständigkeit auch für Teilanlagen übertragen sein (siehe auch DIN VDE 0105-100 (VDE 0105-100):2015-10, 4.3 ).
[QUELLE: DIN VDE 0105-100 (VDE 0105-100):2015-10 , modifiziert, Anmerkung 3 wurde nicht übernommen.]
- bib.al.original-language: en
- bib.dp.publication-date: 2018-06-29
- ids.document: 7104561
- ids.tracing: hash-3ba90a4746350f6db544ba5d43bd2c35659a2e61ec59958aa1dee73590fbb132
- obj.clause-number: 3.3
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-e5fce523d174e23e432066406ec424c5d02fda451f5dd0589ae89fcb8333d301--0IDHF6zpA3wL: Anlagenbetreiber (provision)
Person mit der Gesamtverantwortung für den sicheren Betrieb der elektrischen Anlage, die Regeln und Randbedingungen der Organisation vorgibt
- bib.al.original-language: en
- bib.dp.publication-date: 2018-06-29
- ids.document: 7104561
- ids.tracing: hash-e5fce523d174e23e432066406ec424c5d02fda451f5dd0589ae89fcb8333d301
- obj.clause-number: 3.3
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-f8f3646801b7dfdf1cfeff681c83866b8af3a01ecfcafafe431e628b35faafe4--7cI1sUQbiLWH: Anlagenbetreiber (provision)
[QUELLE: DIN VDE 0105-100 (VDE 0105-100):2015-10 , modifiziert, Anmerkung 3 wurde nicht übernommen.]
- bib.al.original-language: en
- bib.dp.publication-date: 2018-06-29
- ids.document: 7104561
- ids.tracing: hash-f8f3646801b7dfdf1cfeff681c83866b8af3a01ecfcafafe431e628b35faafe4
- obj.clause-number: 3.3
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--8e9b9d1a-8157-4b81-a49d-2d500c597b66--vn5im3M1BEMA: automatische Brandmeldeanlagen (provision)
3.4
automatische Brandmeldeanlagen
Einrichtungen, die den Zweck haben, Schadenfeuer zum frühestmöglichen Zeitpunkt zu erkennen und so zu melden, dass geeignete Gegenmaßnahmen ergriffen werden können (z. B. Räumung von Gebäuden, Herbeirufen von Löschkräften, selbsttätiges Auslösen von Löschvorgängen, Schließen von Feuerschutzabschlüssen, Steuern von Klima- und Lüftungsanlagen)
- bib.al.original-language: en
- bib.dp.publication-date: 2018-06-29
- ids.document: 7104561
- ids.tracing: hash-8b0f321be50d0b09cd0d45b34e4f4ff8e1cc4695d9cabe878492b24a66fb0f61
- obj.clause-number: 3.4
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-dc5854647063bfb43d92a33b0cc010d9ca0df9d6e95fe22c3a7f41d2726d2818--nlTcFtEy1jK3: automatische Brandmeldeanlagen (provision)
Einrichtungen, die den Zweck haben, Schadenfeuer zum frühestmöglichen Zeitpunkt zu erkennen und so zu melden, dass geeignete Gegenmaßnahmen ergriffen werden können (z. B. Räumung von Gebäuden, Herbeirufen von Löschkräften, selbsttätiges Auslösen von Löschvorgängen, Schließen von Feuerschutzabschlüssen, Steuern von Klima- und Lüftungsanlagen)
- bib.al.original-language: en
- bib.dp.publication-date: 2018-06-29
- ids.document: 7104561
- ids.tracing: hash-dc5854647063bfb43d92a33b0cc010d9ca0df9d6e95fe22c3a7f41d2726d2818
- obj.clause-number: 3.4
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--8e9b9d1a-8157-4b81-a49d-2d500c597b66--NLGVytTikXjD: Brandklassen (provision)
3.5
Brandklassen
Einteilung von Bränden in Abhängigkeit des Brennstoffes
Anmerkung 1 zum Begriff: Nach DIN EN 2 werden folgende Brandklassen unterschieden.
- bib.al.original-language: en
- bib.dp.publication-date: 2018-06-29
- ids.document: 7104561
- ids.tracing: hash-f47308a14eb4cf98f1a120f287176757f040c170ccbb0126586455166fbb7530
- obj.clause-number: 3.5
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-dd3729986f2ec7f52f4b0eff2c8f94ea67e9416e94a1866ad55dd6f909a4b53c--KNzI7e7LqoAk: Brandklassen (provision)
Einteilung von Bränden in Abhängigkeit des Brennstoffes
- bib.al.original-language: en
- bib.dp.publication-date: 2018-06-29
- ids.document: 7104561
- ids.tracing: hash-dd3729986f2ec7f52f4b0eff2c8f94ea67e9416e94a1866ad55dd6f909a4b53c
- obj.clause-number: 3.5
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--8e9b9d1a-8157-4b81-a49d-2d500c597b66--Genn9QOn6hr8: Brandklasse A (provision)
3.5.1
Brandklasse A
Brände fester Stoffe, hauptsächlich organischer Natur, die normalerweise unter Glutbildung verbrennen, z. B. Holz, Papier, Stroh, Textilien, Kohle
- bib.al.original-language: en
- bib.dp.publication-date: 2018-06-29
- ids.document: 7104561
- ids.tracing: hash-2972f7fd4c024a40373b4d847bf4d857c98cd5d742ce6af9fda38750ee5003c6
- obj.clause-number: 3.5.1
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-127ea801f52cd5494c2cb0f6de9db9feee2f3a7a8b543368c066db51df4fc6fb--VNEey03DgL2B: Brandklasse A (provision)
Brände fester Stoffe, hauptsächlich organischer Natur, die normalerweise unter Glutbildung verbrennen, z. B. Holz, Papier, Stroh, Textilien, Kohle
- bib.al.original-language: en
- bib.dp.publication-date: 2018-06-29
- ids.document: 7104561
- ids.tracing: hash-127ea801f52cd5494c2cb0f6de9db9feee2f3a7a8b543368c066db51df4fc6fb
- obj.clause-number: 3.5.1
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--8e9b9d1a-8157-4b81-a49d-2d500c597b66--FzGaXIMQQnM4: Brandklasse B (provision)
3.5.2
Brandklasse B
Brände von flüssigen oder flüssig werdenden Stoffen, z. B. Benzin, Benzol, Öle, Fette, Lacke, Teer, Äther, Alkohol, Stearin, Paraffin
- bib.al.original-language: en
- bib.dp.publication-date: 2018-06-29
- ids.document: 7104561
- ids.tracing: hash-7da7063532192cd8b1f95d5c22febb07ec76ff90dbda7da857eca9093010e718
- obj.clause-number: 3.5.2
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-fbb87bbf2b0e2a8c5907dac1d8a11866c0351336a06c070f58b50a6981151c98--1pjjLUpYZJUe: Brandklasse B (provision)
Brände von flüssigen oder flüssig werdenden Stoffen, z. B. Benzin, Benzol, Öle, Fette, Lacke, Teer, Äther, Alkohol, Stearin, Paraffin
- bib.al.original-language: en
- bib.dp.publication-date: 2018-06-29
- ids.document: 7104561
- ids.tracing: hash-fbb87bbf2b0e2a8c5907dac1d8a11866c0351336a06c070f58b50a6981151c98
- obj.clause-number: 3.5.2
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--8e9b9d1a-8157-4b81-a49d-2d500c597b66--mQFjZIMmJWOS: Brandklasse C (provision)
3.5.3
Brandklasse C
Brände von Gasen, z. B. Methan, Propan, Wasserstoff, Acetylen, Erdgas
- bib.al.original-language: en
- bib.dp.publication-date: 2018-06-29
- ids.document: 7104561
- ids.tracing: hash-d78a1204583e79ef1e5014a1bab44c398d72dab495537faec09281d9171708e3
- obj.clause-number: 3.5.3
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-ff8384402aa6b894850492b0769ae4c39cade700f41cbf00de3eef4ba4db8d25--OjaCH0bNHDKo: Brandklasse C (provision)
Brände von Gasen, z. B. Methan, Propan, Wasserstoff, Acetylen, Erdgas
- bib.al.original-language: en
- bib.dp.publication-date: 2018-06-29
- ids.document: 7104561
- ids.tracing: hash-ff8384402aa6b894850492b0769ae4c39cade700f41cbf00de3eef4ba4db8d25
- obj.clause-number: 3.5.3
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--8e9b9d1a-8157-4b81-a49d-2d500c597b66--9fxPlWTfWsfp: Brandklasse D (provision)
3.5.4
Brandklasse D
Brände von Metallen, z. B. Aluminium, Magnesium und ihre Legierungen, Natrium, Kalium
- bib.al.original-language: en
- bib.dp.publication-date: 2018-06-29
- ids.document: 7104561
- ids.tracing: hash-2560783041d4911495fd11257d574d6c4cdddcf11853a04f897eb46ab30fa6ad
- obj.clause-number: 3.5.4
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-2e6615682125bf20f1f4f4c1b13c5262d976f84384593fdca4b7fee501c5e346--yCbFY5njGj8b: Brandklasse D (provision)
Brände von Metallen, z. B. Aluminium, Magnesium und ihre Legierungen, Natrium, Kalium
- bib.al.original-language: en
- bib.dp.publication-date: 2018-06-29
- ids.document: 7104561
- ids.tracing: hash-2e6615682125bf20f1f4f4c1b13c5262d976f84384593fdca4b7fee501c5e346
- obj.clause-number: 3.5.4
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--8e9b9d1a-8157-4b81-a49d-2d500c597b66--4117085RUjx0: Brandklasse F (provision)
3.5.5
Brandklasse F
Brände von Speiseölen/-fetten (pflanzliche oder tierische Öle und Fette) in Frittier- und Fettbackgeräten und anderen Kücheneinrichtungen und -geräten
- bib.al.original-language: en
- bib.dp.publication-date: 2018-06-29
- ids.document: 7104561
- ids.tracing: hash-2650e3853b3c559df384387fd101ce987b6f51282ddcafb78f9965abababd169
- obj.clause-number: 3.5.5
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-d731cd4dbcc6131e877cee4e402595e39dba322cb111d7b535810f48c6951667--dKpttFzO1Okv: Brandklasse F (provision)
Brände von Speiseölen/-fetten (pflanzliche oder tierische Öle und Fette) in Frittier- und Fettbackgeräten und anderen Kücheneinrichtungen und -geräten
- bib.al.original-language: en
- bib.dp.publication-date: 2018-06-29
- ids.document: 7104561
- ids.tracing: hash-d731cd4dbcc6131e877cee4e402595e39dba322cb111d7b535810f48c6951667
- obj.clause-number: 3.5.5
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--8e9b9d1a-8157-4b81-a49d-2d500c597b66--EqccP3xbFKyd: dezentrale Stromerzeugungsanlagen (provision)
3.6
dezentrale Stromerzeugungsanlagen
Anlagen zur Erzeugung von elektrischem Strom für den Eigenverbrauch und/oder zur Einspeisung in das öffentliche Energieversorgungsnetz
Anmerkung 1 zum Begriff: Dazu gehören z. B. Photovoltaik-Stromversorgungssysteme (PV-Anlagen), Brennstoffzellenanlagen, Windenergieanlagen. Dezentrale Stromerzeugungsanlagen können mit oder ohne elektrische Energiespeicher betrieben werden.
- bib.al.original-language: en
- bib.dp.publication-date: 2018-06-29
- ids.document: 7104561
- ids.tracing: hash-cf2ceee6cc1f924c0f5516853fc7cbe36f518354c2bccfc3e798b44756ad7665
- obj.clause-number: 3.6
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-5ae446db7fc8489de9f530271447d15c12c70326988808ff3db8938633606c74--ZHakaLf7DmWH: dezentrale Stromerzeugungsanlagen (provision)
Anlagen zur Erzeugung von elektrischem Strom für den Eigenverbrauch und/oder zur Einspeisung in das öffentliche Energieversorgungsnetz
- bib.al.original-language: en
- bib.dp.publication-date: 2018-06-29
- ids.document: 7104561
- ids.tracing: hash-5ae446db7fc8489de9f530271447d15c12c70326988808ff3db8938633606c74
- obj.clause-number: 3.6
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--8e9b9d1a-8157-4b81-a49d-2d500c597b66--QgOtNna0Himi: Druckluftschaum (en: compressed air foam) (provision)
3.7
Druckluftschaum (en: compressed air foam)
Löschschaum, erzeugt durch eine Druckluftschaumanlage
Anmerkung 1 zum Begriff: Druckluftschaumanlagen sind in DIN EN 16327 definiert.
- bib.al.original-language: en
- bib.dp.publication-date: 2018-06-29
- ids.document: 7104561
- ids.tracing: hash-d10c098e1a5b711c0d3e419022aa7bb59d255b12bb4eacab3a93c862b0705432
- obj.clause-number: 3.7
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-98328a545228110ed15de1cd93777c2f3ddebf65d7c1423675f93005f1129ae6--KmNuEFGWyNi3: Druckluftschaum (en: compressed air foam) (provision)
Löschschaum, erzeugt durch eine Druckluftschaumanlage
- bib.al.original-language: en
- bib.dp.publication-date: 2018-06-29
- ids.document: 7104561
- ids.tracing: hash-98328a545228110ed15de1cd93777c2f3ddebf65d7c1423675f93005f1129ae6
- obj.clause-number: 3.7
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--8e9b9d1a-8157-4b81-a49d-2d500c597b66--sNERbQflphjP (provision)
3.8
elektrische Anlage
Anlagen mit elektrischen Betriebsmitteln zur Erzeugung, Übertragung, Umwandlung, Verteilung und Anwendung elektrischer Energie
Den elektrischen Betriebsmitteln gleichgesetzt werden Werkzeuge, Ausrüstungen, Schutz- und Hilfsmittel, soweit an diese Anforderungen hinsichtlich der elektrischen Sicherheit gestellt werden.
Anmerkung 1 zum Begriff: Dies schließt Energiequellen ein wie Batterien, Kondensatoren und alle anderen Quellen gespeicherter elektrischer Energie.
[QUELLE: DIN VDE 0105-100 (VDE 0105-100):2015-10 ]
- bib.al.original-language: en
- bib.dp.publication-date: 2018-06-29
- ids.document: 7104561
- ids.tracing: hash-09cc6b33c55cd6f5fb19504ffef7d1d63f4b0c4abfd30d5210c8f05373982a44
- obj.clause-number: 3.8
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-2f6a5e1d3badf39594ae45321a3d987efcfe39f5373bc391034a7e59389940ac--YO7SBUJdoEKD (provision)
Anlagen mit elektrischen Betriebsmitteln zur Erzeugung, Übertragung, Umwandlung, Verteilung und Anwendung elektrischer Energie
- bib.al.original-language: en
- bib.dp.publication-date: 2018-06-29
- ids.document: 7104561
- ids.tracing: hash-2f6a5e1d3badf39594ae45321a3d987efcfe39f5373bc391034a7e59389940ac
- obj.clause-number: 3.8
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-76162ce1baa50548852d8a095beff7f3aecf055695c88ef7ccf682e3c6561d39--nPazZb7f0AuO (provision)
Den elektrischen Betriebsmitteln gleichgesetzt werden Werkzeuge, Ausrüstungen, Schutz- und Hilfsmittel, soweit an diese Anforderungen hinsichtlich der elektrischen Sicherheit gestellt werden.
- bib.al.original-language: en
- bib.dp.publication-date: 2018-06-29
- ids.document: 7104561
- ids.tracing: hash-76162ce1baa50548852d8a095beff7f3aecf055695c88ef7ccf682e3c6561d39
- obj.clause-number: 3.8
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-8a9eb2fe7e916d99c55e00ac8b96d9b25afe0c6a466bf0ba73f50a8e167469b3--JAoWRZGwQJ47 (provision)
Anmerkung 1 zum Begriff: Dies schließt Energiequellen ein wie Batterien, Kondensatoren und alle anderen Quellen gespeicherter elektrischer Energie.
- bib.al.original-language: en
- bib.dp.publication-date: 2018-06-29
- ids.document: 7104561
- ids.tracing: hash-8a9eb2fe7e916d99c55e00ac8b96d9b25afe0c6a466bf0ba73f50a8e167469b3
- obj.clause-number: 3.8
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-3119490ac6abcf7f6ea91197871fab87b78e4f7fb36ea2cb65cffb5e31b25992--N6cCNmsS5URV (provision)
[QUELLE: DIN VDE 0105-100 (VDE 0105-100):2015-10 ]
- bib.al.original-language: en
- bib.dp.publication-date: 2018-06-29
- ids.document: 7104561
- ids.tracing: hash-3119490ac6abcf7f6ea91197871fab87b78e4f7fb36ea2cb65cffb5e31b25992
- obj.clause-number: 3.8
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--8e9b9d1a-8157-4b81-a49d-2d500c597b66--d6OIgL3GxoOB: Elektrofachkraft (provision)
3.9
Elektrofachkraft
ist, wer aufgrund seiner fachlichen Ausbildung, Kenntnisse und Erfahrungen sowie Kenntnis der einschlägigen Normen die ihm übertragenen Arbeiten beurteilen und mögliche Gefahren erkennen kann
Anmerkung 1 zum Begriff: Zur Beurteilung der fachlichen Ausbildung kann auch eine mehrjährige Tätigkeit auf dem betreffenden Arbeitsgebiet herangezogen werden.
[QUELLE: DIN VDE 0105-100 (VDE 0105-100):2015-10 ]
- bib.al.original-language: en
- bib.dp.publication-date: 2018-06-29
- ids.document: 7104561
- ids.tracing: hash-51a4ce7c10b71707fbbf788688b09c7f23686458d7024f554e80a0bbd8f8a97d
- obj.clause-number: 3.9
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-5e91bb282b1d6388826d1dec666bf89c0faedff3f127a9b91d72d65504884f7d--iwOS88AlHlQj: Elektrofachkraft (provision)
ist, wer aufgrund seiner fachlichen Ausbildung, Kenntnisse und Erfahrungen sowie Kenntnis der einschlägigen Normen die ihm übertragenen Arbeiten beurteilen und mögliche Gefahren erkennen kann
- bib.al.original-language: en
- bib.dp.publication-date: 2018-06-29
- ids.document: 7104561
- ids.tracing: hash-5e91bb282b1d6388826d1dec666bf89c0faedff3f127a9b91d72d65504884f7d
- obj.clause-number: 3.9
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--8e9b9d1a-8157-4b81-a49d-2d500c597b66--AGME1f2atdZ8: elektrotechnisch unterwiesene Person (provision)
3.10
elektrotechnisch unterwiesene Person
ist, wer durch eine Elektrofachkraft über die ihr übertragenen Aufgaben und die möglichen Gefahren bei unsachgemäßem Verhalten unterrichtet und erforderlichenfalls angelernt sowie über die notwendigen Schutzeinrichtungen und Schutzmaßnahmen unterwiesen wurde
[QUELLE: DIN VDE 0105-100 (VDE 0105-100):2015-10 ]
- bib.al.original-language: en
- bib.dp.publication-date: 2018-06-29
- ids.document: 7104561
- ids.tracing: hash-40542dbf6c7f886d24d9a45abc95203a0b4f2dd659177b37e110791214bf346f
- obj.clause-number: 3.10
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-f5426ddf9b9cd977c73255012c6bd7e802a88c18f30583bd20e1595ea7b6b16b--RX0C6qR1pGkm: elektrotechnisch unterwiesene Person (provision)
ist, wer durch eine Elektrofachkraft über die ihr übertragenen Aufgaben und die möglichen Gefahren bei unsachgemäßem Verhalten unterrichtet und erforderlichenfalls angelernt sowie über die notwendigen Schutzeinrichtungen und Schutzmaßnahmen unterwiesen wurde
[QUELLE: DIN VDE 0105-100 (VDE 0105-100):2015-10 ]
- bib.al.original-language: en
- bib.dp.publication-date: 2018-06-29
- ids.document: 7104561
- ids.tracing: hash-f5426ddf9b9cd977c73255012c6bd7e802a88c18f30583bd20e1595ea7b6b16b
- obj.clause-number: 3.10
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--8e9b9d1a-8157-4b81-a49d-2d500c597b66--Qhy1PgEHiSmX: fahrbare Feuerlöscher (provision)
3.11
fahrbare Feuerlöscher
fahrbare Feuerlöschgeräte ohne eigenen Kraftantrieb
- bib.al.original-language: en
- bib.dp.publication-date: 2018-06-29
- ids.document: 7104561
- ids.tracing: hash-4da202e4083f7a38d9ce0bb0bad259d8387a64a64dac790b458828eb9f36d8ed
- obj.clause-number: 3.11
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-d992fce3ef79a10fb5180fc3113062441ae890250e92e9e36ad968d300abb39d--f3qm55ceOqiR: fahrbare Feuerlöscher (provision)
fahrbare Feuerlöschgeräte ohne eigenen Kraftantrieb
- bib.al.original-language: en
- bib.dp.publication-date: 2018-06-29
- ids.document: 7104561
- ids.tracing: hash-d992fce3ef79a10fb5180fc3113062441ae890250e92e9e36ad968d300abb39d
- obj.clause-number: 3.11
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--8e9b9d1a-8157-4b81-a49d-2d500c597b66--TlEkjppIcxoW (provision)
3.12
Fahrleitung
Leitersystem zur Versorgung von Fahrzeugen mit elektrischer Energie über Stromabnahmeeinrichtungen
Anmerkung 1 zum Begriff: Es umfasst alle Leiter, die zur Stromabnahme nötig sind, sowie Stromschienen und beinhaltet Folgendes:
- Verstärkungsleitungen,
- Schalterquerleitungen,
- Trennschalter,
- Streckentrenner,
- Überspannungsschutzeinrichtungen,
- Trageinrichtungen, die nicht von den Leitern isoliert sind,
- Isolatoren, die mit aktiven Teilen verbunden sind.
Nicht zur Fahrleitung gehören:
- Speiseleitungen,
- Erdseile und Rückleiter.
[QUELLE: DIN EN 50122-1 (VDE 0115-3):2017-10 ]
- bib.al.original-language: en
- bib.dp.publication-date: 2018-06-29
- ids.document: 7104561
- ids.tracing: hash-6aeda75546d20b05c99d981343d51117fb41393410ef2ff52169127f61f915e5
- obj.clause-number: 3.12
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-ac8e17c05407417d7a2dd52858e7d88cca9ec34ec818f2c6dffb8b3091b0fb65--RYGdxIV4yyLP (provision)
Leitersystem zur Versorgung von Fahrzeugen mit elektrischer Energie über Stromabnahmeeinrichtungen
- bib.al.original-language: en
- bib.dp.publication-date: 2018-06-29
- ids.document: 7104561
- ids.tracing: hash-ac8e17c05407417d7a2dd52858e7d88cca9ec34ec818f2c6dffb8b3091b0fb65
- obj.clause-number: 3.12
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-9b3803ce6ed12d078b9e231d26e9ec4967f670db9fd2c8d52761108ded4be0d4--kzb96xl0ZcAS (provision)
Anmerkung 1 zum Begriff: Es umfasst alle Leiter, die zur Stromabnahme nötig sind, sowie Stromschienen und beinhaltet Folgendes:
- Verstärkungsleitungen,
- Schalterquerleitungen,
- Trennschalter,
- Streckentrenner,
- Überspannungsschutzeinrichtungen,
- Trageinrichtungen, die nicht von den Leitern isoliert sind,
- Isolatoren, die mit aktiven Teilen verbunden sind.
- bib.al.original-language: en
- bib.dp.publication-date: 2018-06-29
- ids.document: 7104561
- ids.tracing: hash-9b3803ce6ed12d078b9e231d26e9ec4967f670db9fd2c8d52761108ded4be0d4
- obj.clause-number: 3.12
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-c1b53d79c33eb7374b75bdbc65e0725fececee393857d1113bb9673036114b56--5VmPwSM9ctsK (provision)
Nicht zur Fahrleitung gehören:
- Speiseleitungen,
- Erdseile und Rückleiter.
- bib.al.original-language: en
- bib.dp.publication-date: 2018-06-29
- ids.document: 7104561
- ids.tracing: hash-c1b53d79c33eb7374b75bdbc65e0725fececee393857d1113bb9673036114b56
- obj.clause-number: 3.12
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-bd108df986e5c6080f84f557aaa67ddb9fe3ed78a97ac97dbca84384b64079f4--Z4N6nBVh6u53 (provision)
[QUELLE: DIN EN 50122-1 (VDE 0115-3):2017-10 ]
- bib.al.original-language: en
- bib.dp.publication-date: 2018-06-29
- ids.document: 7104561
- ids.tracing: hash-bd108df986e5c6080f84f557aaa67ddb9fe3ed78a97ac97dbca84384b64079f4
- obj.clause-number: 3.12
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--8e9b9d1a-8157-4b81-a49d-2d500c597b66--UsafzxnosKwk: Freileitung (provision)
3.13
Freileitung
elektrische Leitung, deren Leiter oberirdisch geführt sind, im Allgemeinen mit Hilfe von Isolatoren und geeigneten Stützpunkten
Anmerkung 1 zum Begriff: Bestimmte Freileitungen können mit isolierten Leitern ausgerüstet sein.
[QUELLE: IEV 466-01-02]
- bib.al.original-language: en
- bib.dp.publication-date: 2018-06-29
- ids.document: 7104561
- ids.tracing: hash-f714783f11653ff27e80735c17bffeb77a94942b51e98bc459630868c709c161
- obj.clause-number: 3.13
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-a71fb0c7ef9278408b410008590626aa1ec619d8b2fdcb52a79fbb78da1ba8ee--o8ScLGldWQw7: Freileitung (provision)
elektrische Leitung, deren Leiter oberirdisch geführt sind, im Allgemeinen mit Hilfe von Isolatoren und geeigneten Stützpunkten
- bib.al.original-language: en
- bib.dp.publication-date: 2018-06-29
- ids.document: 7104561
- ids.tracing: hash-a71fb0c7ef9278408b410008590626aa1ec619d8b2fdcb52a79fbb78da1ba8ee
- obj.clause-number: 3.13
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--8e9b9d1a-8157-4b81-a49d-2d500c597b66--9ZSCKzH8LAfH: Hochvolt HV (provision)
3.14
Hochvolt HV
Spannungen oberhalb von AC 25 V oder DC 60 V in Elektrofahrzeugen
Anmerkung 1 zum Begriff: Dies schließt Fahrzeuge mit Hybridantrieben und Fahrzeuge mit Brennstoffzellenantrieben ein.
- bib.al.original-language: en
- bib.dp.publication-date: 2018-06-29
- ids.document: 7104561
- ids.tracing: hash-c8b6fe1c5211e168a388eb68cb48ab3f33a07c2f1402ced1c5df406181d2cc3a
- obj.clause-number: 3.14
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-fc76f244e9613a62c29c570c354aa70e0cc1669bd30578c840d1ac9542cd2c36--UG86NxhuhAqw: Hochvolt HV (provision)
Spannungen oberhalb von AC 25 V oder DC 60 V in Elektrofahrzeugen
- bib.al.original-language: en
- bib.dp.publication-date: 2018-06-29
- ids.document: 7104561
- ids.tracing: hash-fc76f244e9613a62c29c570c354aa70e0cc1669bd30578c840d1ac9542cd2c36
- obj.clause-number: 3.14
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--8e9b9d1a-8157-4b81-a49d-2d500c597b66--dzIP3aSULBrr: Hochspannungsanlage (provision)
3.15
Hochspannungsanlage
elektrische Anlage, die mit einer Nennspannung größer AC 1 000 V (Wechselspannung) oder DC 1 500 V (Gleichspannung) betrieben wird
Anmerkung 1 zum Begriff: Zu den Hochspannungsanlagen gehören insbesondere Anlagen, die der Stromerzeugung oder der Umwandlung, Verteilung und Anwendung elektrischer Energie dienen, z. B. Kraftwerke, Schalt- und Umspannanlagen, Freileitungen, Kabelanlagen sowie Anlagen und Fahrzeuge von elektrischen Bahnen.
Anmerkung 2 zum Begriff: Hochspannungsanlagen – mit Ausnahme von Freileitungen und Fahrleitungen elektrischer Bahnen – sind in der Regel durch das Warnschild W012 „Warnung vor elektrischer Spannung“ nach DIN EN ISO 7010 oder Warnschild „gefährliche Spannung“ nach IEC 60417-5036 gekennzeichnet.
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Anmerkung 3 zum Begriff:
- bib.al.original-language: en
- bib.dp.publication-date: 2018-06-29
- ids.document: 7104561
- ids.tracing: hash-39dc352453d4748a97ca6f940c382d00565642905c60e1cb54ac7ad02392a27b
- obj.clause-number: 3.15
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-d9a494f80fd3b17494fda7299f2048720012ba840fa435753420a33714ee2ccc--35I7L51jiWeJ: Hochspannungsanlage (provision)
elektrische Anlage, die mit einer Nennspannung größer AC 1 000 V (Wechselspannung) oder DC 1 500 V (Gleichspannung) betrieben wird
- bib.al.original-language: en
- bib.dp.publication-date: 2018-06-29
- ids.document: 7104561
- ids.tracing: hash-d9a494f80fd3b17494fda7299f2048720012ba840fa435753420a33714ee2ccc
- obj.clause-number: 3.15
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--8e9b9d1a-8157-4b81-a49d-2d500c597b66--c71EmnXZZMre: Niederspannungsanlage (provision)
3.16
Niederspannungsanlage
elektrische Anlage, die mit einer Nennspannung kleiner oder gleich AC 1 000 V (Wechselspannung) oder DC 1 500 V (Gleichspannung) betrieben wird
Anmerkung 1 zum Begriff: Zu den Niederspannungsanlagen gehören z. B. Stromerzeugungs- und Verteilungsanlagen, Ortsnetze, Hausinstallationen sowie Installationen für industrielle, gewerbliche und landwirtschaftliche Betriebe, die Fahrleitungen und Installationen der mit Gleichspannung (Niederspannung) betriebenen Straßen- und Stadtbahnen, Oberleitungsbusse (Obusse), Fernmelde- und Informationsverarbeitungsanlagen.
- bib.al.original-language: en
- bib.dp.publication-date: 2018-06-29
- ids.document: 7104561
- ids.tracing: hash-d84114f7bcf5a38008e75e2a33f38fa1e833b1e14c848621b9fd7be00cd13b97
- obj.clause-number: 3.16
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-9355ace62a880f1e2c2f99bbc579af1a2b7f1ca4a3c9269fb861d391237b7f4e--ZWpuHBlIDxPf: Niederspannungsanlage (provision)
elektrische Anlage, die mit einer Nennspannung kleiner oder gleich AC 1 000 V (Wechselspannung) oder DC 1 500 V (Gleichspannung) betrieben wird
- bib.al.original-language: en
- bib.dp.publication-date: 2018-06-29
- ids.document: 7104561
- ids.tracing: hash-9355ace62a880f1e2c2f99bbc579af1a2b7f1ca4a3c9269fb861d391237b7f4e
- obj.clause-number: 3.16
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--8e9b9d1a-8157-4b81-a49d-2d500c597b66--u9dTgGRKHV6J: ortsfeste Löschanlagen (provision)
3.17
ortsfeste Löschanlagen
fest installierte Löscheinrichtungen, deren Auslösung von Hand und/oder automatisch erfolgt
- bib.al.original-language: en
- bib.dp.publication-date: 2018-06-29
- ids.document: 7104561
- ids.tracing: hash-f877f37e7c7a898725aec815ae9fde024b4a2a035410916843aa88b9f5e912cf
- obj.clause-number: 3.17
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-a3a03a1cfa048b79ee7a8cfc5fa66d0cd4e67c705e29ba9c6f27f8e763feffb9--BOGk7Dca9QQ3: ortsfeste Löschanlagen (provision)
fest installierte Löscheinrichtungen, deren Auslösung von Hand und/oder automatisch erfolgt
- bib.al.original-language: en
- bib.dp.publication-date: 2018-06-29
- ids.document: 7104561
- ids.tracing: hash-a3a03a1cfa048b79ee7a8cfc5fa66d0cd4e67c705e29ba9c6f27f8e763feffb9
- obj.clause-number: 3.17
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--8e9b9d1a-8157-4b81-a49d-2d500c597b66--yY4o361zp5Zk: SPE-PRCD (provision)
3.18
SPE-PRCD
Differenzstromeinrichtung mit Fehlerstrom-, Schutzleiterbruch-, Schutzleiterspannungs- und Fremdspannungsüberwachung
[QUELLE: E DIN IEC 62335 (VDE 0661-20):2008-06]
- bib.al.original-language: en
- bib.dp.publication-date: 2018-06-29
- ids.document: 7104561
- ids.tracing: hash-04912881b6e4eedbaf4be1ab6058829952d7abef77eebd6f208bb41178a4f001
- obj.clause-number: 3.18
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-fd4bf1a12311c764dba8dc1410eeb250a144a7a3ff5cb8fe55c53109618d61cd--4N1nzmRrk0Pf: SPE-PRCD (provision)
Differenzstromeinrichtung mit Fehlerstrom-, Schutzleiterbruch-, Schutzleiterspannungs- und Fremdspannungsüberwachung
- bib.al.original-language: en
- bib.dp.publication-date: 2018-06-29
- ids.document: 7104561
- ids.tracing: hash-fd4bf1a12311c764dba8dc1410eeb250a144a7a3ff5cb8fe55c53109618d61cd
- obj.clause-number: 3.18
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-fca5feb0223ead3aac09812e8f3fb9d426bb1a109d0c7eccf3285af30f558cf7--gkP3Kc5n3wP8: SPE-PRCD (provision)
[QUELLE: E DIN IEC 62335 (VDE 0661-20):2008-06]
- bib.al.original-language: en
- bib.dp.publication-date: 2018-06-29
- ids.document: 7104561
- ids.tracing: hash-fca5feb0223ead3aac09812e8f3fb9d426bb1a109d0c7eccf3285af30f558cf7
- obj.clause-number: 3.18
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--8e9b9d1a-8157-4b81-a49d-2d500c597b66--YzFLomnrpXwx: Strahlrohr (provision)
3.19
Strahlrohr
Armaturen zur Abgabe von Löschmitteln
- bib.al.original-language: en
- bib.dp.publication-date: 2018-06-29
- ids.document: 7104561
- ids.tracing: hash-d818843ffe2fd225994c78206f8aa6c34c398aa609a271e21526efe258bbc745
- obj.clause-number: 3.19
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-01b0fdcb0e771ac0f47dabf252b7f23483a77259c2bc65df5c243a455bb26b1d--gnyAV7kXnCJP: Strahlrohr (provision)
Armaturen zur Abgabe von Löschmitteln
- bib.al.original-language: en
- bib.dp.publication-date: 2018-06-29
- ids.document: 7104561
- ids.tracing: hash-01b0fdcb0e771ac0f47dabf252b7f23483a77259c2bc65df5c243a455bb26b1d
- obj.clause-number: 3.19
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--8e9b9d1a-8157-4b81-a49d-2d500c597b66--KezVPy6wjmTC: anderes Strahlrohr (provision)
3.19.1
anderes Strahlrohr
Strahlrohr, das weder Mehrzweckstrahlrohr noch Hohlstrahlrohr ist
- bib.al.original-language: en
- bib.dp.publication-date: 2018-06-29
- ids.document: 7104561
- ids.tracing: hash-8bb43fbf495b8daf8aa6479efc541a2ed57eacdeab87a6e97d69411882fd0be8
- obj.clause-number: 3.19.1
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-39b5ac55ccf71dca6464af55d93a01afdebbc34cc0e3436a0cd36afeffcdfbf5--GT6P52Hiht3X: anderes Strahlrohr (provision)
Strahlrohr, das weder Mehrzweckstrahlrohr noch Hohlstrahlrohr ist
- bib.al.original-language: en
- bib.dp.publication-date: 2018-06-29
- ids.document: 7104561
- ids.tracing: hash-39b5ac55ccf71dca6464af55d93a01afdebbc34cc0e3436a0cd36afeffcdfbf5
- obj.clause-number: 3.19.1
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--8e9b9d1a-8157-4b81-a49d-2d500c597b66--7gYqJjVJEMIf: Hohlstrahlrohr (provision)
3.19.2
Hohlstrahlrohr
Strahlrohr einschließlich einer Schließvorrichtung und einer einstellbaren Strahlform
[QUELLE: DIN EN 15182-2:2010-04, 3.1, verändert übernommen]
- bib.al.original-language: en
- bib.dp.publication-date: 2018-06-29
- ids.document: 7104561
- ids.tracing: hash-cc483f6fbaf80c4105540a3dac469e71c9e3eb651abddab0d5086866563c5015
- obj.clause-number: 3.19.2
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-c1b503944e579c8ef5864c15116984e162e6729532790d9f933425ed550d89f6--TOIzNsqO2eyA: Hohlstrahlrohr (provision)
Strahlrohr einschließlich einer Schließvorrichtung und einer einstellbaren Strahlform
[QUELLE: DIN EN 15182-2:2010-04, 3.1, verändert übernommen]
- bib.al.original-language: en
- bib.dp.publication-date: 2018-06-29
- ids.document: 7104561
- ids.tracing: hash-c1b503944e579c8ef5864c15116984e162e6729532790d9f933425ed550d89f6
- obj.clause-number: 3.19.2
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--8e9b9d1a-8157-4b81-a49d-2d500c597b66--Czd57A1KjvEF: Mehrzweckstrahlrohr (provision)
3.19.3
Mehrzweckstrahlrohr
Das Mehrzweckstrahlrohr ist eine Armatur zur gezielten Abgabe vornehmlich von Löschwasser in Form eines Voll- oder Sprühstrahls
Anmerkung 1 zum Begriff: Strahlrohre CM haben einen Mundstückdurchmesser von 9 mm und einen Düsendurchmesser von 12 mm.
Anmerkung 2 zum Begriff: Strahlrohre BM haben einen Mundstückdurchmesser von 16 mm und einen Düsendurchmesser von 22 mm.
[QUELLE: DIN 14365-1:1991-02]
- bib.al.original-language: en
- bib.dp.publication-date: 2018-06-29
- ids.document: 7104561
- ids.tracing: hash-e470d668507655895bbcd7f31328ab19c22c5183d1b9990c14b08ef82c698eb8
- obj.clause-number: 3.19.3
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-2d89c7bfb03881faec45f1fbcf820e22f7b5e1ac76167d9a51537599034f979c--GaJFa3spH5zo: Mehrzweckstrahlrohr (provision)
Das Mehrzweckstrahlrohr ist eine Armatur zur gezielten Abgabe vornehmlich von Löschwasser in Form eines Voll- oder Sprühstrahls
- bib.al.original-language: en
- bib.dp.publication-date: 2018-06-29
- ids.document: 7104561
- ids.tracing: hash-2d89c7bfb03881faec45f1fbcf820e22f7b5e1ac76167d9a51537599034f979c
- obj.clause-number: 3.19.3
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-0a20066337a788a0c3943f17661508ba743b03cbec8d11c9c4305a3b7a810cff--gaEmeUrQzyB1: Mehrzweckstrahlrohr (provision)
[QUELLE: DIN 14365-1:1991-02]
- bib.al.original-language: en
- bib.dp.publication-date: 2018-06-29
- ids.document: 7104561
- ids.tracing: hash-0a20066337a788a0c3943f17661508ba743b03cbec8d11c9c4305a3b7a810cff
- obj.clause-number: 3.19.3
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--8e9b9d1a-8157-4b81-a49d-2d500c597b66--yjYGkS8XgPoP: tragbarer Feuerlöscher (provision)
3.20
tragbarer Feuerlöscher
Feuerlöscher, der getragen und von Hand bedient werden kann und im betriebsbereiten Zustand eine Masse von nicht mehr als 20 kg hat
[QUELLE: DIN EN 3-7:2007-10]
- bib.al.original-language: en
- bib.dp.publication-date: 2018-06-29
- ids.document: 7104561
- ids.tracing: hash-f189926c259d1e8ce24831c9d58ae8132db9f72eaf1ac3d3737132d2d55a812c
- obj.clause-number: 3.20
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-81c327dc535707f52cb556aacb0be08b4554e9aa20542cdc241f04dbba63e0d3--cwz1cXoZy4km: tragbarer Feuerlöscher (provision)
Feuerlöscher, der getragen und von Hand bedient werden kann und im betriebsbereiten Zustand eine Masse von nicht mehr als 20 kg hat
[QUELLE: DIN EN 3-7:2007-10]
- bib.al.original-language: en
- bib.dp.publication-date: 2018-06-29
- ids.document: 7104561
- ids.tracing: hash-81c327dc535707f52cb556aacb0be08b4554e9aa20542cdc241f04dbba63e0d3
- obj.clause-number: 3.20
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--8e9b9d1a-8157-4b81-a49d-2d500c597b66--fdInVCjMiTjp (provision)
3.21
trockener Raum
Raum oder bestimmter Bereich innerhalb eines Raums, in dem in der Regel kein Kondenswasser auftritt oder in dem die Luft nicht mit Feuchtigkeit gesättigt ist
Anmerkung 1 zum Begriff: Hierzu gehören z. B. Wohnräume (auch Hotelzimmer), Büros; weiterhin können hierzu gehören:
- Geschäftsräume, Verkaufsräume, Dachböden, Treppenhäuser, beheizte oder belüftbare Keller;
- Küchen in Wohnungen und Baderäume in Wohnungen und Hotels gelten in Bezug auf die Installation als trockene Räume, da in ihnen nur zeitweise Feuchtigkeit auftritt.
- bib.al.original-language: en
- bib.dp.publication-date: 2018-06-29
- ids.document: 7104561
- ids.tracing: hash-6e000676e3686a713e477cd84b430797476b3b610b95262d7855ae0f52511d51
- obj.clause-number: 3.21
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-8290e73c2eccde74afe27577b262d099a375304964ee61a67509b9e254875ee0--rOLmW7YbK0jg (provision)
Raum oder bestimmter Bereich innerhalb eines Raums, in dem in der Regel kein Kondenswasser auftritt oder in dem die Luft nicht mit Feuchtigkeit gesättigt ist
- bib.al.original-language: en
- bib.dp.publication-date: 2018-06-29
- ids.document: 7104561
- ids.tracing: hash-8290e73c2eccde74afe27577b262d099a375304964ee61a67509b9e254875ee0
- obj.clause-number: 3.21
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-4cea2d2d5135dbf2e93a8f0fdc12f3e963fe13b505b02704e9fce28051c1a252--e3z9TzO1YJNW (provision)
Anmerkung 1 zum Begriff: Hierzu gehören z. B. Wohnräume (auch Hotelzimmer), Büros; weiterhin können hierzu gehören:
- Geschäftsräume, Verkaufsräume, Dachböden, Treppenhäuser, beheizte oder belüftbare Keller;
- Küchen in Wohnungen und Baderäume in Wohnungen und Hotels gelten in Bezug auf die Installation als trockene Räume, da in ihnen nur zeitweise Feuchtigkeit auftritt.
- bib.al.original-language: en
- bib.dp.publication-date: 2018-06-29
- ids.document: 7104561
- ids.tracing: hash-4cea2d2d5135dbf2e93a8f0fdc12f3e963fe13b505b02704e9fce28051c1a252
- obj.clause-number: 3.21
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### tr--8e9b9d1a-8157-4b81-a49d-2d500c597b66--7FDbRVppzxVe: unterbrechungsfreies Stromversorgungssystem USV (provision)
3.22
unterbrechungsfreies Stromversorgungssystem USV
Kombination von Stromrichtern, Schaltern und Energiespeichern (wie Batterien), die ein Stromversorgungssystem bildet, das bei Ausfall der Eingangsversorgung eine beständige Versorgung der Last sicherstellt
[QUELLE: DIN EN 62040-1 (VDE 0558-510):2009-06 ]
- bib.al.original-language: en
- bib.dp.publication-date: 2018-06-29
- ids.document: 7104561
- ids.tracing: hash-308a436f3dadf8d2d386340581c130f2ff53c06e4729a6b7504411539cbf89c0
- obj.clause-number: 3.22
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-94ddf48f6e209679607ede638132c192c8eeae428feb729d7db0960001603ba6--qd6tC6KJzY2j: unterbrechungsfreies Stromversorgungssystem USV (provision)
Kombination von Stromrichtern, Schaltern und Energiespeichern (wie Batterien), die ein Stromversorgungssystem bildet, das bei Ausfall der Eingangsversorgung eine beständige Versorgung der Last sicherstellt
[QUELLE: DIN EN 62040-1 (VDE 0558-510):2009-06 ]
- bib.al.original-language: en
- bib.dp.publication-date: 2018-06-29
- ids.document: 7104561
- ids.tracing: hash-94ddf48f6e209679607ede638132c192c8eeae428feb729d7db0960001603ba6
- obj.clause-number: 3.22
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

## R108: Vorbereitende Maßnahmen (heading)
- bib.al.original-language: en
- bib.dp.publication-date: 2018-06-29
- ids.document: 7104561
- obj.clause-number: 4
- obj.element-name: heading
- obj.language: de
- obj.specobject-type: heading
- ChapterName: 4 Vorbereitende Maßnahmen

### R109: 4.1 (heading)
- bib.al.original-language: en
- bib.dp.publication-date: 2018-06-29
- ids.document: 7104561
- obj.element-name: heading
- obj.language: de
- obj.specobject-type: heading

#### tr--hash-074c3735b63be0fdb109a2f795b9f49d020b1f8c7055d1269b970a41c2f9d81e--d15LMEBUrahB (provision)
Verständnisvolle Zusammenarbeit zwischen Feuerwehr und dem Anlagenbetreiber elektrischer Anlagen ist anzustreben.
- bib.al.original-language: en
- bib.dp.publication-date: 2018-06-29
- ids.document: 7104561
- ids.tracing: hash-074c3735b63be0fdb109a2f795b9f49d020b1f8c7055d1269b970a41c2f9d81e
- obj.clause-number: 4.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-ee9984b3fd293faca96da24cafe9482cdc15f84fdd63a5751b4e27bcdd600fb1--1TuQ8ytBoDzk (provision)
Diesem Zweck dienen unter anderem die Absprachen zwischen Feuerwehr und Anlagenbetreiber über die im Einsatz notwendigen Maßnahmen nach 4.2 bis 4.5.
- bib.al.original-language: en
- bib.dp.publication-date: 2018-06-29
- ids.document: 7104561
- ids.tracing: hash-ee9984b3fd293faca96da24cafe9482cdc15f84fdd63a5751b4e27bcdd600fb1
- obj.clause-number: 4.1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R112

### R112: 4.2 (heading)
- bib.al.original-language: en
- bib.dp.publication-date: 2018-06-29
- ids.document: 7104561
- obj.element-name: heading
- obj.language: de
- obj.specobject-type: heading

#### tr--hash-00543c24b736b5d0fd91f779fe6d70fd0c238399062085becd81ae7aeb7f73c0--yTlCrFTambCf (provision)
Der Anlagenbetreiber gibt der Feuerwehr Aufklärung über besondere Gefährdungen und Schwierigkeiten, die bei Brandbekämpfung und bei technischer Hilfeleistung auftreten können.
- bib.al.original-language: en
- bib.dp.publication-date: 2018-06-29
- ids.document: 7104561
- ids.tracing: hash-00543c24b736b5d0fd91f779fe6d70fd0c238399062085becd81ae7aeb7f73c0
- obj.clause-number: 4.2
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-4ffb48e15f5aa3baedd89ca37014a52b85dcbba43628ac2e63039bf746b3a6e8--vLyyOF23sWfK (provision)
Grundlage können Feuerwehrpläne nach DIN 14095 sein, die der raschen Orientierung und der Beurteilung der Lage dienen.
- bib.al.original-language: en
- bib.dp.publication-date: 2018-06-29
- ids.document: 7104561
- ids.tracing: hash-4ffb48e15f5aa3baedd89ca37014a52b85dcbba43628ac2e63039bf746b3a6e8
- obj.clause-number: 4.2
- obj.element-name: paragraph
- obj.language: de
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

### R115: 4.3 (heading)
- bib.al.original-language: en
- bib.dp.publication-date: 2018-06-29
- ids.document: 7104561
- obj.element-name: heading
- obj.language: de
- obj.specobject-type: heading

#### tr--hash-b8ed7c7abc7a89e3d7e83ed3c4acbc53dcafe1fd9ed42384bdcfe309937158ab--xk1HoJSv2PW7 (provision)
Isolier-/Kühl-Flüssigkeiten und -Gase können besondere Gefährdungen darstellen.
- bib.al.original-language: en
- bib.dp.publication-date: 2018-06-29
- ids.document: 7104561
- ids.tracing: hash-b8ed7c7abc7a89e3d7e83ed3c4acbc53dcafe1fd9ed42384bdcfe309937158ab
- obj.clause-number: 4.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-554122efbac2bc02331f72f2bce505cf22679e6cfb89cebca01e1b1eab731732--IL0EWtzZxtpo (provision)
Einschlägige bundes- und landesrechtliche Festlegungen sind zu beachten.
- bib.al.original-language: en
- bib.dp.publication-date: 2018-06-29
- ids.document: 7104561
- ids.tracing: hash-554122efbac2bc02331f72f2bce505cf22679e6cfb89cebca01e1b1eab731732
- obj.clause-number: 4.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--8e9b9d1a-8157-4b81-a49d-2d500c597b66--UamRHHesUFko: , Note (provision)
ANMERKUNG 1:
PCB-haltige elektrische Betriebsmittel sind vom Anlagenbetreiber durch Schilder augenfällig gekennzeichnet.
ANMERKUNG 2 Siehe Anhang A „Beurteilung von Gefahren, die von PCB-haltigen Betriebsmitteln ausgehen können.
- bib.al.original-language: en
- bib.dp.publication-date: 2018-06-29
- ids.document: 7104561
- ids.tracing: hash-e4484b7d8c83ec6c6a2db75afeb0155f78b3ba786f4bb6cc360dd0ec0d52c690
- obj.clause-number: 4.3
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> R316

### R119: 4.4 (heading)
- bib.al.original-language: en
- bib.dp.publication-date: 2018-06-29
- ids.document: 7104561
- obj.element-name: heading
- obj.language: de
- obj.specobject-type: heading

#### tr--hash-852e5093a747ceb351b7ee6707afa2212b7bd01977311b539246aa1bccf695ac--0QCUHKI19iLT (provision)
Den Einsatz einer Werkfeuerwehr und die Einsatzleitung bestimmen landesrechtliche Vorschriften.
- bib.al.original-language: en
- bib.dp.publication-date: 2018-06-29
- ids.document: 7104561
- ids.tracing: hash-852e5093a747ceb351b7ee6707afa2212b7bd01977311b539246aa1bccf695ac
- obj.clause-number: 4.4
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### R121: 4.5 (heading)
- bib.al.original-language: en
- bib.dp.publication-date: 2018-06-29
- ids.document: 7104561
- obj.element-name: heading
- obj.language: de
- obj.specobject-type: heading

#### tr--hash-94a0a7bd69b73cf22f206f20e6179805ebe1632ef737be98e8d978d839f1f2d5--MCeQYTMMxfKa (provision)
Der Anlagenbetreiber von Hochspannungsanlagen bezeichnet die Stelle oder nennt Personen, die bei Bränden und technischer Hilfeleistung für den Kontakt mit der Feuerwehr zuständig sind, und gibt die in Frage kommenden Kommunikationsmöglichkeiten bekannt.
- bib.al.original-language: en
- bib.dp.publication-date: 2018-06-29
- ids.document: 7104561
- ids.tracing: hash-94a0a7bd69b73cf22f206f20e6179805ebe1632ef737be98e8d978d839f1f2d5
- obj.clause-number: 4.5
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

## R123: Maßnahmen bei Bränden und technischen Hilfeleistungen (heading)
- bib.al.original-language: en
- bib.dp.publication-date: 2018-06-29
- ids.document: 7104561
- obj.clause-number: 5
- obj.element-name: heading
- obj.language: de
- obj.specobject-type: heading
- ChapterName: 5 Maßnahmen bei Bränden und technischen Hilfeleistungen

### R124: Allgemeine Maßnahmen (heading)
- bib.al.original-language: en
- bib.dp.publication-date: 2018-06-29
- ids.document: 7104561
- obj.clause-number: 5.1
- obj.element-name: heading
- obj.language: de
- obj.specobject-type: heading
- ChapterName: 5.1 Allgemeine Maßnahmen

#### R125: 5.1.1 (heading)
- bib.al.original-language: en
- bib.dp.publication-date: 2018-06-29
- ids.document: 7104561
- obj.element-name: heading
- obj.language: de
- obj.specobject-type: heading

##### tr--hash-f123ac43785888a0c1c6bf3ee5d9f07e7d8f560c3b0010d88b23e7af836c93e1--FuptM3YsNNgF (provision)
Feuerwehr und Anlagenbetreiber verständigen sich im Brandfall und bei technischer Hilfeleistung entsprechend den getroffenen Vereinbarungen gegenseitig.
- bib.al.original-language: en
- bib.dp.publication-date: 2018-06-29
- ids.document: 7104561
- ids.tracing: hash-f123ac43785888a0c1c6bf3ee5d9f07e7d8f560c3b0010d88b23e7af836c93e1
- obj.clause-number: 5.1.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### R127: 5.1.2 (heading)
- bib.al.original-language: en
- bib.dp.publication-date: 2018-06-29
- ids.document: 7104561
- obj.element-name: heading
- obj.language: de
- obj.specobject-type: heading

##### tr--hash-70e017315b377585fe439d9697b5b9e7d0aaaafc6d5486798d6bce4bb915f80a--hsWNCLHxJhLB (provision)
Beauftragte des Anlagenbetreibers haben sich auf Anforderung der Feuerwehr zur Verfügung zu stellen und erforderlichenfalls auszuweisen.
- bib.al.original-language: en
- bib.dp.publication-date: 2018-06-29
- ids.document: 7104561
- ids.tracing: hash-70e017315b377585fe439d9697b5b9e7d0aaaafc6d5486798d6bce4bb915f80a
- obj.clause-number: 5.1.2
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### R129: 5.1.3 (heading)
- bib.al.original-language: en
- bib.dp.publication-date: 2018-06-29
- ids.document: 7104561
- obj.element-name: heading
- obj.language: de
- obj.specobject-type: heading

##### tr--hash-40764bf775a014fcda7d11919153409b6191aac46999d08c94b17f56a5d9debe--HVH11fcrQGG5 (provision)
Maßnahmen bei Überflutung zur Sicherstellung der Personensicherheit.
- bib.al.original-language: en
- bib.dp.publication-date: 2018-06-29
- ids.document: 7104561
- ids.tracing: hash-40764bf775a014fcda7d11919153409b6191aac46999d08c94b17f56a5d9debe
- obj.clause-number: 5.1.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-3799f884948e954e385ad3ee8650e5958bbfb7a9426bad61a66e9ac6131b6c6e--NDXPLGXNIRmc (provision)
Durch Überflutungen (z. B. Rohrbrüche, Hochwasser, Löschwasser) können unter Spannung stehende Teile mit Wasser in Berührung kommen und Personen gefährden.
- bib.al.original-language: en
- bib.dp.publication-date: 2018-06-29
- ids.document: 7104561
- ids.tracing: hash-3799f884948e954e385ad3ee8650e5958bbfb7a9426bad61a66e9ac6131b6c6e
- obj.clause-number: 5.1.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-c01acb52633348e6e4be0d10266c8ca381d1f41c7473ae7c4bcadafb1a4f0409--vwpgzYu6x8FA (provision)
Diese Bereiche sind rechtzeitig an sicherer Stelle frei- oder auszuschalten.
- bib.al.original-language: en
- bib.dp.publication-date: 2018-06-29
- ids.document: 7104561
- ids.tracing: hash-c01acb52633348e6e4be0d10266c8ca381d1f41c7473ae7c4bcadafb1a4f0409
- obj.clause-number: 5.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-e02aa269e142b7649708cdd77db74bac265c37600d1e9b518469d3f5e497543a--qvNQsWtvW8bK (provision)
Sind elektrische Anlagen bereits überflutet, dürfen diese Bereiche nur nach festgestellter Spannungsfreiheit betreten werden.
- bib.al.original-language: en
- bib.dp.publication-date: 2018-06-29
- ids.document: 7104561
- ids.tracing: hash-e02aa269e142b7649708cdd77db74bac265c37600d1e9b518469d3f5e497543a
- obj.clause-number: 5.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-31152bc2afc983ad2ed744b917a978ff708397c3e4ac1e9842463f09bc6336bf--YUdXwHcU2onn (provision)
Der zuständige Netzbetreiber ist zu informieren.
- bib.al.original-language: en
- bib.dp.publication-date: 2018-06-29
- ids.document: 7104561
- ids.tracing: hash-31152bc2afc983ad2ed744b917a978ff708397c3e4ac1e9842463f09bc6336bf
- obj.clause-number: 5.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-1f7d0fe90187b06df4e180dd85bd17dfad60c4332cffafa0f9d3112268eb775e--qWgSG6PnatbG (provision)
Dieser lässt die erforderlichen Freischaltmaßnahmen durchführen oder entscheidet, dass die überfluteten unter Spannung stehenden Anlagen weiter betrieben werden.
- bib.al.original-language: en
- bib.dp.publication-date: 2018-06-29
- ids.document: 7104561
- ids.tracing: hash-1f7d0fe90187b06df4e180dd85bd17dfad60c4332cffafa0f9d3112268eb775e
- obj.clause-number: 5.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-471886b97b01996a376510fd0b1ea2c1b0521f627367134f5bb4c010954439b6--NP7CdrfoorqY (provision)
Bei dezentralen Stromerzeugungsanlagen sind die Maßnahmen nach Tabelle 1 anzuwenden.
- bib.al.original-language: en
- bib.dp.publication-date: 2018-06-29
- ids.document: 7104561
- ids.tracing: hash-471886b97b01996a376510fd0b1ea2c1b0521f627367134f5bb4c010954439b6
- obj.clause-number: 5.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> tr--8e9b9d1a-8157-4b81-a49d-2d500c597b66--4VeEarYSHDTs

##### tr--hash-5a9fe46adcd2de838ba771d29a3d4e55ff65a3c32c48f72b5491f053c15de13c--ikqsFt3o8x2Q (provision)
Die Einheiten der Gefahrenabwehr (z. B. Feuerwehr) setzen nur eigene ortsveränderliche elektrische Betriebsmittel (z. B. Tauchpumpen) ein, die den zu erwartenden Einsatzbedingungen genügen.
- bib.al.original-language: en
- bib.dp.publication-date: 2018-06-29
- ids.document: 7104561
- ids.tracing: hash-5a9fe46adcd2de838ba771d29a3d4e55ff65a3c32c48f72b5491f053c15de13c
- obj.clause-number: 5.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-41370ce28a9dfa5d3ea492f98dd0985f1a1969497860cdc75b9fa44b9267694c--PqIIUU6GBaWq (provision)
Vorrangig sind für die Stromversorgung die eigenen Stromerzeuger einzusetzen.
- bib.al.original-language: en
- bib.dp.publication-date: 2018-06-29
- ids.document: 7104561
- ids.tracing: hash-41370ce28a9dfa5d3ea492f98dd0985f1a1969497860cdc75b9fa44b9267694c
- obj.clause-number: 5.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-ed7592d5868986e777a11dfb8613c9e6845338149de126888c1fe0a30e4163ce--XUZZVoCRUbRd (provision)
Sollte in Ausnahmefällen aufgrund der Einsatzsituation ein anderer Speisepunkt erforderlich sein, darf der Anschluss nur über eine Fehlerstromschutzeinrichtung des Typs SPE-PRCD für den Personenschutz erfolgen.
- bib.al.original-language: en
- bib.dp.publication-date: 2018-06-29
- ids.document: 7104561
- ids.tracing: hash-ed7592d5868986e777a11dfb8613c9e6845338149de126888c1fe0a30e4163ce
- obj.clause-number: 5.1.3
- obj.element-name: paragraph
- obj.language: de
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-054ad0eeff2d6e8a9a93a59700a565e0e03f4b7581addebf686b0611e69e6d5c--0o1Du2Lcid5b (provision)
Dieser ist möglichst nahe an der Stromentnahmestelle zu installieren.
- bib.al.original-language: en
- bib.dp.publication-date: 2018-06-29
- ids.document: 7104561
- ids.tracing: hash-054ad0eeff2d6e8a9a93a59700a565e0e03f4b7581addebf686b0611e69e6d5c
- obj.clause-number: 5.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### R141: 5.1.4 (heading)
- bib.al.original-language: en
- bib.dp.publication-date: 2018-06-29
- ids.document: 7104561
- obj.element-name: heading
- obj.language: de
- obj.specobject-type: heading

##### tr--hash-a31e67b73889637cfa0d7ba9c71be8382c4f7bc9fdf0d4107d197f5e7653acaa--3s4iNYrYSqUh (provision)
Bei Bränden und technischer Hilfeleistung in elektrischen Anlagen (Elektrizitätsversorgungsnetzen und/oder dezentrale Stromversorgungsanlagen) oder in deren Nähe sind, soweit überhaupt eine Notwendigkeit dazu vorliegt, nur die betroffenen oder unmittelbar bedrohten Teile spannungsfrei zu schalten.
- bib.al.original-language: en
- bib.dp.publication-date: 2018-06-29
- ids.document: 7104561
- ids.tracing: hash-a31e67b73889637cfa0d7ba9c71be8382c4f7bc9fdf0d4107d197f5e7653acaa
- obj.clause-number: 5.1.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-85d892ee4fe13a6a4550817cdb7453c177bc21e4cc70b695c75ca01e3cac3d89--Q2sEOBx7ylNT (provision)
Einige Stromversorgungsanlagen können systembedingt nicht spannungsfrei geschaltet werden (siehe Tabelle 1).
- bib.al.original-language: en
- bib.dp.publication-date: 2018-06-29
- ids.document: 7104561
- ids.tracing: hash-85d892ee4fe13a6a4550817cdb7453c177bc21e4cc70b695c75ca01e3cac3d89
- obj.clause-number: 5.1.4
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> tr--8e9b9d1a-8157-4b81-a49d-2d500c597b66--4VeEarYSHDTs

##### tr--hash-e3255aa67756a4a48631b90a83a2b4eafe148fa602f3957082e4030ff0ebd62a--7cx6iVD4OLIx (provision)
Grundsatz muss sein, dass so wenig wie möglich ausgeschaltet wird.
- bib.al.original-language: en
- bib.dp.publication-date: 2018-06-29
- ids.document: 7104561
- ids.tracing: hash-e3255aa67756a4a48631b90a83a2b4eafe148fa602f3957082e4030ff0ebd62a
- obj.clause-number: 5.1.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-d753ebcda6ad0f9ae42b07115cc9f9935c885d805ef47a2cccdd2f56e7a17d0e--VdCfSLC7Lpo0 (provision)
Mit Rücksicht auf die Nachteile für die Brandbekämpfung und bei technischer Hilfeleistung sowie für die Allgemeinheit sind Abschaltungen nur in Absprache zwischen Feuerwehr und dem Anlagenbetreiber vorzunehmen.
- bib.al.original-language: en
- bib.dp.publication-date: 2018-06-29
- ids.document: 7104561
- ids.tracing: hash-d753ebcda6ad0f9ae42b07115cc9f9935c885d805ef47a2cccdd2f56e7a17d0e
- obj.clause-number: 5.1.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### tr--8e9b9d1a-8157-4b81-a49d-2d500c597b66--xNH09NHLpHp0: , Note (provision)
ANMERKUNG 1:
Dadurch soll z. B. vermieden werden:
- bib.al.original-language: en
- bib.dp.publication-date: 2018-06-29
- ids.document: 7104561
- ids.tracing: hash-f64699d422245c3d11de92de4aa0353e6579eea6117a32e6cf7a224b6a65d71a
- obj.clause-number: 5.1.4
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### tr--8e9b9d1a-8157-4b81-a49d-2d500c597b66--tDhkL0Uc7scY (provision)
- Gefährdung von Patienten;
- Stilllegen der Wasserversorgung;
- Gefährdungen und Schäden durch die Unterbrechung von Betriebsabläufen;
- Stillstand von Aufzügen und elektrisch betätigten Toren;
- Verdunklung von Straßen.
- bib.al.original-language: en
- bib.dp.publication-date: 2018-06-29
- ids.document: 7104561
- ids.tracing: hash-fef7c18e2692fdfe5706662577340ea1b29ffc60ef76d3cba1a231c2bcab4e3d
- obj.clause-number: 5.1.4
- obj.element-name: unordered-list
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### tr--8e9b9d1a-8157-4b81-a49d-2d500c597b66--Xq8TVn4yQF3C: , Note (provision)
ANMERKUNG 2 Lichtbögen können im Allgemeinen nur durch Ausschalten unterbrochen werden.
- bib.al.original-language: en
- bib.dp.publication-date: 2018-06-29
- ids.document: 7104561
- ids.tracing: hash-50ccd56c4133795adf120d90534d1d336e4ef35379c925041bba9133095749e4
- obj.clause-number: 5.1.4
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### tr--8e9b9d1a-8157-4b81-a49d-2d500c597b66--KiugxFGy1vxf: , Note (provision)
ANMERKUNG 3 Die Benutzung von Aufzügen – mit Ausnahme von Feuerwehraufzügen – ist wegen der Gefahr eines Stromausfalls gefährlich und zu vermeiden.
- bib.al.original-language: en
- bib.dp.publication-date: 2018-06-29
- ids.document: 7104561
- ids.tracing: hash-02ec52dfdb1922d5f8d3c3c36dd262086e40123837cb41ccca9ab31cdfd8c0b4
- obj.clause-number: 5.1.4
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### tr--hash-64e05425cbc1cbf5ef6af358f2aceb4f1e16122d9676829fcc99da344109520a--bOWnlvSeBtu5 (provision)
Anlagen, die dem Brandschutz und der Brandbekämpfung dienen (z. B. Rauch- und Wärmeabzugsanlagen, Sprinkler- und Sprühwasserlöschanlagen), dürfen ohne zwingende Notwendigkeit nicht außer Betrieb gesetzt werden.
- bib.al.original-language: en
- bib.dp.publication-date: 2018-06-29
- ids.document: 7104561
- ids.tracing: hash-64e05425cbc1cbf5ef6af358f2aceb4f1e16122d9676829fcc99da344109520a
- obj.clause-number: 5.1.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-3de9c857a5d228d976d695abf653bd8533c76a591d7c502c8b9968bbf02394ad--7z4QH2jfmoUn (provision)
Durch Schalten elektrischer Betriebsmittel können erhöhte Brand- und Explosionsgefahren auftreten.
- bib.al.original-language: en
- bib.dp.publication-date: 2018-06-29
- ids.document: 7104561
- ids.tracing: hash-3de9c857a5d228d976d695abf653bd8533c76a591d7c502c8b9968bbf02394ad
- obj.clause-number: 5.1.4
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--8e9b9d1a-8157-4b81-a49d-2d500c597b66--4VeEarYSHDTs: Besonderheiten bei dezentralen Stromerzeugungsanlagen oder anderen EnergiesystemenBrandbekämpfung und technische Hilfeleistung sind grundsätzlich möglich, wenn die Abstände nach den Tabellen 2 bis 8 eingehalten werden. Darüber hinaus sind nachstehende Maßnahmen hilfreich. (provision)
Tabelle 1 — Besonderheiten bei dezentralen Stromerzeugungsanlagen oder anderen EnergiesystemenBrandbekämpfung und technische Hilfeleistung sind grundsätzlich möglich, wenn die Abstände nach den Tabellen 2 bis 8 eingehalten werden. Darüber hinaus sind nachstehende Maßnahmen hilfreich.
| Energiesystem | Maßnahme | Restgefährdung | Anmerkung |
| --- | --- | --- | --- |
| 1. PV-Anlage | – | Selbst bei durch eine Elektrofachkraft festgestellter Spannungsfreiheit können beim Trennen von Leitungen/Steckverbindern Lichtbögen entstehen. | Trotz Abschaltungen kann nicht von einer vollständigen Spannungsfreiheit der PV-Anlage ausgegangen werden. Daher gilt der Grundsatz Abstand halten. Durch Mondlicht oder künstliches Licht (Scheinwerfer) tritt keine elektrische Gefährdung auf (siehe auch Anhang B „Erläuterungen“). |
| - 2) Elektro- und Hybridfahrzeuge | Deaktivieren des Hochvoltsystems (falls das Rückhaltesystem (z. B. Airbag) ausgelöst hat, ist dies in der Regel sichergestellt). 1. Abklemmen der 12 V/24 V-Batterie oder 2. HV-Wartungsschalter (Service Disconnect) betätigen oder 3. fahrzeugspezifische Trennvorrichtungen betätigen. | Siehe 5.1.5 Besondere Maßnahmen bei Lithium-Ionen-Akkumulatoren. . | Brände können mit Wasser gelöscht werden. Sollten Personen durch technische Hilfeleistung aus dem Fahrzeug zu befreien sein, ist davon auszugehen, dass das Rückhaltesystem ausgelöst hat und das HV-System deaktiviert wurde. HV-Kabel sind orange. HV-Komponenten sind durch das Bildzeichen 5036 nach IEC 60417-DB:2002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 gekennzeichnet. |
| - 3) Batterieanlage (z. B. Sicherheitsstromversorgung, USV-Anlage) | Unter Last dürfen - Sicherungen nicht gezogen und - Kabel/Leitungen nicht gelöst oder getrennt werden. | Spannung bleibt in der eigentlichen Batterieanlage bis zur ersten Abschalt-/ Trennein-richtung bestehen; Gefährdung durch Lichtbogen bei Kurzschluss oder beim Abschalten. | Das Abschalten der Batterie ist nicht möglich. Die von der Batterie versorgte elektrische Anlage kann jedoch in der Regel freigeschaltet werden. |
| - 4) Stromerzeugungsaggregat | Not-Ausschalter betätigen oder Stromerzeuger ausschalten. Zusätzlich Brennstoffzufuhr unterbrechen. | Spannung steht noch bis zum Stillstand des Aggregats an. | – |
| - 5) Brennstoffzellenanlage | Not-Ausschalter betätigen. Zusätzlich Brennstoffzufuhr unterbrechen. | Spannung kann nach Unterbrechen der Brennstoffzufuhr weiter anstehen. | Die Dauer der Restgefährdung ist abhängig von dem dann noch zur Verfügung stehenden Restbrennstoff. |
| - 6) Windenergieanlage | Sicherung der Einsatzstelle, dabei Bauhöhe, Windrichtung und Windstärke berücksichtigen. | Einsturzgefahr, Gefährdung durch wegfliegende Trümmer, Brandausbreitung. | Gegebenenfalls kontrolliert abbrennen lassen. |
- bib.al.original-language: en
- bib.dp.publication-date: 2018-06-29
- ids.document: 7104561
- ids.tracing: hash-f53a11e91f1b7c6992f801114f8a96628c99b8670b405fac07b7c653ae0e2ed3
- obj.clause-number: Tabelle 1
- obj.element-name: table
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> tr--8e9b9d1a-8157-4b81-a49d-2d500c597b66--8nilfDyyzJnb
- cross-reference -> R318
- cross-reference -> R153

#### R153: Besondere Maßnahmen bei Lithium-Ionen-Akkumulatoren (heading)
- bib.al.original-language: en
- bib.dp.publication-date: 2018-06-29
- ids.document: 7104561
- obj.clause-number: 5.1.5
- obj.element-name: heading
- obj.language: de
- obj.specobject-type: heading
- ChapterName: 5.1.5 Besondere Maßnahmen bei Lithium-Ionen-Akkumulatoren

##### R154: Allgemeines (heading)
- bib.al.original-language: en
- bib.dp.publication-date: 2018-06-29
- ids.document: 7104561
- obj.clause-number: 5.1.5.1
- obj.element-name: heading
- obj.language: de
- obj.specobject-type: heading
- ChapterName: 5.1.5.1 Allgemeines

###### tr--hash-e6dd92b9fca397e2c41b2ccb8f4df70013455d6041863dd12235560437b2d96b--1EFCFU99MFht: Allgemeines (provision)
Lithium-Ionen-Akkumulatoren sind vor allem anzutreffen:
- bei elektromobilen Anwendungen (z. B. Elektro- und Hybrid-Fahrzeugen, Pedelecs);
- in stationären Speichern (z. B. Haushaltsspeichern in Verbindung mit PV-Anlagen, Quartierspeichern und Großspeichern der Netzbetreiber);
- in Lagerstätten (z. B. Produktion, Handel, Entsorgung).
- bib.al.original-language: en
- bib.dp.publication-date: 2018-06-29
- ids.document: 7104561
- ids.tracing: hash-e6dd92b9fca397e2c41b2ccb8f4df70013455d6041863dd12235560437b2d96b
- obj.clause-number: 5.1.5.1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### R156: Gefährdungen (heading)
- bib.al.original-language: en
- bib.dp.publication-date: 2018-06-29
- ids.document: 7104561
- obj.clause-number: 5.1.5.2
- obj.element-name: heading
- obj.language: de
- obj.specobject-type: heading
- ChapterName: 5.1.5.2 Gefährdungen

###### tr--hash-93c09022768028cde328e41322f9824dbcedf046f096031072eb8ae10ed3aa9d--R4y8lEEVS8aR: Gefährdungen (provision)
Folgende Gefährdungen können von Lithium-Ionen-Akkumulatoren ausgehen:
- elektrische (z. B. Rückspannung in die Elektroinstallation trotz Trennung vom örtlichen Stromversorgungsnetz);
- thermische (z. B. extreme Brandausbreitung);
- chemische (z. B. Flusssäure, giftige und brennbare Gase).
- bib.al.original-language: en
- bib.dp.publication-date: 2018-06-29
- ids.document: 7104561
- ids.tracing: hash-93c09022768028cde328e41322f9824dbcedf046f096031072eb8ae10ed3aa9d
- obj.clause-number: 5.1.5.2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### tr--hash-8eefde8e61933c39447a4327f6cbe13c485357566e1d650463e74c75954b9421--1IJlFhfidpKg: Gefährdungen (provision)
Diese vorstehend genannten Gefährdungen können auch zeitverzögert bis zu mehrere Stunden nach einer Schadenseinwirkung auftreten.
- bib.al.original-language: en
- bib.dp.publication-date: 2018-06-29
- ids.document: 7104561
- ids.tracing: hash-8eefde8e61933c39447a4327f6cbe13c485357566e1d650463e74c75954b9421
- obj.clause-number: 5.1.5.2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### tr--hash-4167c8d46b16a42685df2d2d2a97b59e5132a6c6288e605d8d3a1bc3d1d06d15--hJYsfatxzXRg: Gefährdungen (provision)
Auslöser eines Schadensereignisses können z. B. sein: Blitzeinschlag, Überspannung, Überschwemmung, Brand, mechanische Einwirkung.
- bib.al.original-language: en
- bib.dp.publication-date: 2018-06-29
- ids.document: 7104561
- ids.tracing: hash-4167c8d46b16a42685df2d2d2a97b59e5132a6c6288e605d8d3a1bc3d1d06d15
- obj.clause-number: 5.1.5.2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### R160: Maßnahmen (heading)
- bib.al.original-language: en
- bib.dp.publication-date: 2018-06-29
- ids.document: 7104561
- obj.clause-number: 5.1.5.3
- obj.element-name: heading
- obj.language: de
- obj.specobject-type: heading
- ChapterName: 5.1.5.3 Maßnahmen

###### tr--hash-770f7aa335e3e6a5484c1d1f55df780e01e9ed06de9ca70dc5f4ddc5b3e87118--WVpi6WZ3psUT: Maßnahmen (provision)
Nur die benötigten Einsatzkräfte dürfen den unmittelbaren Gefahrenbereich (in der Regel den betroffenen Raum) betreten.
- bib.al.original-language: en
- bib.dp.publication-date: 2018-06-29
- ids.document: 7104561
- ids.tracing: hash-770f7aa335e3e6a5484c1d1f55df780e01e9ed06de9ca70dc5f4ddc5b3e87118
- obj.clause-number: 5.1.5.3
- obj.element-name: paragraph
- obj.language: de
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

###### tr--hash-9e68dbf9a69f64651ed4a23cbbc1417efc85103cfb5be32e09ccc6a248ba6053--bEjUPiJ4GgYM: Maßnahmen (provision)
Dabei sollten diese Einsatzkräfte den größtmöglichen Abstand halten bzw. aufgrund der extremen Brandausbreitung aus der Deckung arbeiten.
- bib.al.original-language: en
- bib.dp.publication-date: 2018-06-29
- ids.document: 7104561
- ids.tracing: hash-9e68dbf9a69f64651ed4a23cbbc1417efc85103cfb5be32e09ccc6a248ba6053
- obj.clause-number: 5.1.5.3
- obj.element-name: paragraph
- obj.language: de
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

###### tr--hash-76c309ec49f8fded106bf4e58618addab7d7c2adc751cbf10f6edb095414407b--oYl6sdXC8AKo: Maßnahmen (provision)
Bei Verdacht auf beschädigte Lithium-Ionen-Akkumulatoren ist der Anlagenbetreiber über das Risiko der verzögerten Reaktion und des weiteren Betriebes zu informieren, damit er die sofortige Stilllegung und einen zeitnahen Ausbau des Lithium-Ionen-Akkumulators veranlassen kann.
- bib.al.original-language: en
- bib.dp.publication-date: 2018-06-29
- ids.document: 7104561
- ids.tracing: hash-76c309ec49f8fded106bf4e58618addab7d7c2adc751cbf10f6edb095414407b
- obj.clause-number: 5.1.5.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### tr--hash-fd33e1f22679004fd7c41649702dbe6b52b5e327b4c02af3c63f227b1e7b38ef--2c7uhenyS0OL: Maßnahmen (provision)
Beim Einsatz können Personen und Geräte in Kontakt kommen mit:
- Elektrolyt oder
- Zersetzungsprodukten (u. a. Flusssäure in kontaminiertem Löschmittel).
- bib.al.original-language: en
- bib.dp.publication-date: 2018-06-29
- ids.document: 7104561
- ids.tracing: hash-fd33e1f22679004fd7c41649702dbe6b52b5e327b4c02af3c63f227b1e7b38ef
- obj.clause-number: 5.1.5.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### tr--hash-453431b35b98eafcc4adbb3fe497825a4e1836c0e423b1e5601029bccbe1a462--8ZLTRspnYXj2: Maßnahmen (provision)
Für diesen Fall sind Maßnahmen nach der Feuerwehrdienstvorschrift 500 „Einheiten im ABC-Einsatz“ zu ergreifen.
- bib.al.original-language: en
- bib.dp.publication-date: 2018-06-29
- ids.document: 7104561
- ids.tracing: hash-453431b35b98eafcc4adbb3fe497825a4e1836c0e423b1e5601029bccbe1a462
- obj.clause-number: 5.1.5.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### tr--8e9b9d1a-8157-4b81-a49d-2d500c597b66--dgGCWxcGF1zr: Maßnahmen (provision)
1. Brennende Lithium-Ionen-Akkumulatoren.
- bib.al.original-language: en
- bib.dp.publication-date: 2018-06-29
- ids.document: 7104561
- ids.tracing: hash-a8c0ef5b46aa2f2a2919834b34a7d9f790ff9ad1d61874c2c525ef34d3bb9732
- obj.clause-number: 5.1.5.3
- obj.element-name: ordered-list
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### tr--hash-639c1bc11f0ade301d0803dcbec022c5864407eb18ce2878cc6228ab600d1e89--3V4xQNdNftw4: Maßnahmen, list extract (provision)
| → | - Brennende Lithium-Ionen-Akkumulatoren. |
| --- | --- |
- bib.al.original-language: en
- bib.dp.publication-date: 2018-06-29
- ids.document: 7104561
- ids.tracing: hash-639c1bc11f0ade301d0803dcbec022c5864407eb18ce2878cc6228ab600d1e89
- obj.clause-number: 5.1.5.3
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### tr--hash-7cc88ef2cf7567129816b755ec7fc6529c4b2027ea4b929f773b81353cf470c2--zZG3NXKkktax: Maßnahmen (provision)
Wasser ist aufgrund der Kühlwirkung als Löschmittel zu empfehlen.
- bib.al.original-language: en
- bib.dp.publication-date: 2018-06-29
- ids.document: 7104561
- ids.tracing: hash-7cc88ef2cf7567129816b755ec7fc6529c4b2027ea4b929f773b81353cf470c2
- obj.clause-number: 5.1.5.3
- obj.element-name: paragraph
- obj.language: de
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

###### tr--hash-325ca9a0faf81eb7ff1e6f3eec4c6dc1f9286589615c4284470dc188f571886c--fZyZSd8h5rkV: Maßnahmen (provision)
Brennende Lithium-Ionen-Akkumulatoren sind nur schwer zu löschen.
- bib.al.original-language: en
- bib.dp.publication-date: 2018-06-29
- ids.document: 7104561
- ids.tracing: hash-325ca9a0faf81eb7ff1e6f3eec4c6dc1f9286589615c4284470dc188f571886c
- obj.clause-number: 5.1.5.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### tr--hash-5c74d916b087a034e68d933def802454a9d72c29c0e98c2234db04db551b6062--3XT9wNjA2aWD: Maßnahmen (provision)
Daher liegt das taktische Ziel der Einsatzmaßnahme auf der Verhinderung einer weiteren Brandausbreitung.
- bib.al.original-language: en
- bib.dp.publication-date: 2018-06-29
- ids.document: 7104561
- ids.tracing: hash-5c74d916b087a034e68d933def802454a9d72c29c0e98c2234db04db551b6062
- obj.clause-number: 5.1.5.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### tr--hash-c649dcc0ca5b38c9a68fb81ed2c94e24475968356536303032369e8f4f7c7037--kjHsvbJGvY4Q: Maßnahmen (provision)
Bei Lagerstätten mit Lithium-Ionen-Akkumulatoren sind ggf. Maßnahmen zur Löschwasserrückhaltung erforderlich.
- bib.al.original-language: en
- bib.dp.publication-date: 2018-06-29
- ids.document: 7104561
- ids.tracing: hash-c649dcc0ca5b38c9a68fb81ed2c94e24475968356536303032369e8f4f7c7037
- obj.clause-number: 5.1.5.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### tr--8e9b9d1a-8157-4b81-a49d-2d500c597b66--T4Lt6dUma0MS: Maßnahmen (provision)
- 2) Vermeiden des Entzündens der Lithium-Ionen-Akkumulatoren.
- bib.al.original-language: en
- bib.dp.publication-date: 2018-06-29
- ids.document: 7104561
- ids.tracing: hash-56adb5eb9c1722889a052f45f045acdcee1213502e61037c533822513e6a1726
- obj.clause-number: 5.1.5.3
- obj.element-name: ordered-list
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### tr--hash-91111bc252b0a170435fbec2e16a6f4d7a89d194a09260169145a802e3a6c574--jcRymiCmUBYG: Maßnahmen, list extract (provision)
| → | - Vermeiden des Entzündens der Lithium-Ionen-Akkumulatoren. |
| --- | --- |
- bib.al.original-language: en
- bib.dp.publication-date: 2018-06-29
- ids.document: 7104561
- ids.tracing: hash-91111bc252b0a170435fbec2e16a6f4d7a89d194a09260169145a802e3a6c574
- obj.clause-number: 5.1.5.3
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### tr--hash-141e5b7fda3dc9843351c15e86f0656e3bd1f32fc04d2cc1a26dce4a33fff4bb--2nILyrCmBtNI: Maßnahmen (provision)
Bei oder nach thermischer Einwirkung von außen (Akkumulatortemperatur ab etwa 80 °C) sollte der Lithium-Ionen-Akkumulator gekühlt werden, um sein Entzünden und/oder eine Gasfreisetzung zu verhindern (z. B. bei einem Zimmerbrand).
- bib.al.original-language: en
- bib.dp.publication-date: 2018-06-29
- ids.document: 7104561
- ids.tracing: hash-141e5b7fda3dc9843351c15e86f0656e3bd1f32fc04d2cc1a26dce4a33fff4bb
- obj.clause-number: 5.1.5.3
- obj.element-name: paragraph
- obj.language: de
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

#### R175: 5.1.6 (heading)
- bib.al.original-language: en
- bib.dp.publication-date: 2018-06-29
- ids.document: 7104561
- obj.element-name: heading
- obj.language: de
- obj.specobject-type: heading

##### tr--hash-e6e8d56ebf78bbf26c39019e26ec3908bb06bda619b2bd49a85dff9866e584a3--5BtbxIdSltkX (provision)
Beim Einsatz von Leitern, Teleskopmasten und anderen Geräten dürfen die unter 5.2.4, 5.3.4 und 5.3.5 angegebenen und jeweils zutreffenden Mindestabstände nicht unterschritten werden.
- bib.al.original-language: en
- bib.dp.publication-date: 2018-06-29
- ids.document: 7104561
- ids.tracing: hash-e6e8d56ebf78bbf26c39019e26ec3908bb06bda619b2bd49a85dff9866e584a3
- obj.clause-number: 5.1.6
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R195
- cross-reference -> R209
- cross-reference -> R216

##### tr--hash-930674d826e9dd733fa5cb6a6f3ef1966164afeb53d407fcb3a8aa4b9a42fd25--BnuWFYtTYouU (provision)
Hierbei ist die Annäherung durch Belastungen und Schwankungen zu berücksichtigen.
- bib.al.original-language: en
- bib.dp.publication-date: 2018-06-29
- ids.document: 7104561
- ids.tracing: hash-930674d826e9dd733fa5cb6a6f3ef1966164afeb53d407fcb3a8aa4b9a42fd25
- obj.clause-number: 5.1.6
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### R178: 5.1.7 (heading)
- bib.al.original-language: en
- bib.dp.publication-date: 2018-06-29
- ids.document: 7104561
- obj.element-name: heading
- obj.language: de
- obj.specobject-type: heading

##### tr--hash-77a1e2784ee5056ae4fd0856ff62e3e4f0b79284e12fba5ed8509d4052f6c23f--yeZrvPL0C8GQ (provision)
Nicht vom Brand betroffene elektrische Maschinen, Schalttafeln, Geräte, Fernmeldeanlagen usw. sind nach Möglichkeit vor Löschmitteln zu schützen.
- bib.al.original-language: en
- bib.dp.publication-date: 2018-06-29
- ids.document: 7104561
- ids.tracing: hash-77a1e2784ee5056ae4fd0856ff62e3e4f0b79284e12fba5ed8509d4052f6c23f
- obj.clause-number: 5.1.7
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### R180: 5.1.8 (heading)
- bib.al.original-language: en
- bib.dp.publication-date: 2018-06-29
- ids.document: 7104561
- obj.element-name: heading
- obj.language: de
- obj.specobject-type: heading

##### tr--hash-39421dff154bee6fb7ebc1f27f9452f7b12addf358fe3bbfb8b1c55cd0dc2202--ipNUj8fyKtWz (provision)
Klimaanlagen, Lüftungsanlagen usw. sind so zu steuern, dass eine Ausbreitung von Brandrauch im Gebäude vermieden wird.
- bib.al.original-language: en
- bib.dp.publication-date: 2018-06-29
- ids.document: 7104561
- ids.tracing: hash-39421dff154bee6fb7ebc1f27f9452f7b12addf358fe3bbfb8b1c55cd0dc2202
- obj.clause-number: 5.1.8
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### R182: Besondere Maßnahmen für Niederspannungsanlagen (heading)
- bib.al.original-language: en
- bib.dp.publication-date: 2018-06-29
- ids.document: 7104561
- obj.clause-number: 5.2
- obj.element-name: heading
- obj.language: de
- obj.specobject-type: heading
- ChapterName: 5.2 Besondere Maßnahmen für Niederspannungsanlagen

#### R183: 5.2.1 (heading)
- bib.al.original-language: en
- bib.dp.publication-date: 2018-06-29
- ids.document: 7104561
- obj.element-name: heading
- obj.language: de
- obj.specobject-type: heading

##### tr--hash-582d253abd4451c313bf08b9154f6278c845aba385129b5997b346fd185eccd9--TJ3RPEHrthao (provision)
Sind im Bereich der Einsatzstelle umfangreiche Zerstörungen der Niederspannungsanlagen, insbesondere der Freileitungen, zu erwarten oder bereits eingetreten, so sind die betroffenen Leitungen im Bereich der Einsatzstelle spannungsfrei zu machen [siehe DIN VDE 0105-100 (VDE 0105-100):2015-10, 6.2] .
- bib.al.original-language: en
- bib.dp.publication-date: 2018-06-29
- ids.document: 7104561
- ids.tracing: hash-582d253abd4451c313bf08b9154f6278c845aba385129b5997b346fd185eccd9
- obj.clause-number: 5.2.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### tr--8e9b9d1a-8157-4b81-a49d-2d500c597b66--2CQSlPUIqG9a: , Note (provision)
ANMERKUNG:
Diese Maßnahme ist erforderlich, weil der Isolationszustand, z. B. durch Brandeinwirkung oder Löschmaßnahmen unter Umständen erheblich herabgesetzt werden kann, und weil Freileitungen reißen können.
- bib.al.original-language: en
- bib.dp.publication-date: 2018-06-29
- ids.document: 7104561
- ids.tracing: hash-e6cba068cb024ea4a9e3a99fbb9b1e7d55a0b9cc5216244e85314d47fdbe87b2
- obj.clause-number: 5.2.1
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### tr--hash-3767106f191aa0dbe308322201a9e9a2b2bbd7afc801cdd6913ccb06ef1d4ee9--oQptFJKQflco (provision)
Eine Berührung von herabgefallenen Leitungen, auch wenn sie am Boden liegen, und eine Berührung der im normalen Zustand nicht unter Spannung stehenden Metallteile, z. B. Maschinen, Fernmelde-Freileitungen, Antennen, Blechdächer und -wände, Regenrinnen, Wasser- oder Gasleitungen, Metallzäune, kann gefährlich sein.
- bib.al.original-language: en
- bib.dp.publication-date: 2018-06-29
- ids.document: 7104561
- ids.tracing: hash-3767106f191aa0dbe308322201a9e9a2b2bbd7afc801cdd6913ccb06ef1d4ee9
- obj.clause-number: 5.2.1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-cc5edea638d0393a6126310c452fa91ce90fafaa3d30b51dc67f601d05b666ce--LrLpUH4Kfeg3 (provision)
Diese Metallteile können unter Umständen unter Spannung stehen.
- bib.al.original-language: en
- bib.dp.publication-date: 2018-06-29
- ids.document: 7104561
- ids.tracing: hash-cc5edea638d0393a6126310c452fa91ce90fafaa3d30b51dc67f601d05b666ce
- obj.clause-number: 5.2.1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### R188: 5.2.2 (heading)
- bib.al.original-language: en
- bib.dp.publication-date: 2018-06-29
- ids.document: 7104561
- obj.element-name: heading
- obj.language: de
- obj.specobject-type: heading

##### tr--hash-4fd471ac2fa1787ed73ffd663c4943442e0626f70f33d13425a2c29df723a94b--NzLIyXe7Gayt (provision)
Schalthandlungen in Niederspannungsanlagen dürfen nur von Elektrofachkräften oder elektrotechnisch unterwiesenen Personen vorgenommen werden.
- bib.al.original-language: en
- bib.dp.publication-date: 2018-06-29
- ids.document: 7104561
- ids.tracing: hash-4fd471ac2fa1787ed73ffd663c4943442e0626f70f33d13425a2c29df723a94b
- obj.clause-number: 5.2.2
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-7ee73994c4915f8a833c0aea84f6b96a5beca12ec8e3435b1cc750f25fd67b47--OB84NhZmtwWw (provision)
Hiervon ausgenommen sind Hausinstallationen.
- bib.al.original-language: en
- bib.dp.publication-date: 2018-06-29
- ids.document: 7104561
- ids.tracing: hash-7ee73994c4915f8a833c0aea84f6b96a5beca12ec8e3435b1cc750f25fd67b47
- obj.clause-number: 5.2.2
- obj.element-name: paragraph
- obj.language: de
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

###### tr--8e9b9d1a-8157-4b81-a49d-2d500c597b66--3WWlslYcJwEc: , Note (provision)
ANMERKUNG:
Zur Hausinstallation im Sinne dieser Norm gehören auch elektromedizinische Geräte, Leuchtröhrenanlagen, z. B. für Reklame, die zwar mit Hochspannung betrieben werden, jedoch an die Hausinstallation angeschlossen sind und dort geschaltet werden können.
- bib.al.original-language: en
- bib.dp.publication-date: 2018-06-29
- ids.document: 7104561
- ids.tracing: hash-36a5aa0e27516286212b104846bb9235252de54b46a195dbe3a4cf6c40a73b7b
- obj.clause-number: 5.2.2
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### R192: 5.2.3 (heading)
- bib.al.original-language: en
- bib.dp.publication-date: 2018-06-29
- ids.document: 7104561
- obj.element-name: heading
- obj.language: de
- obj.specobject-type: heading

##### tr--hash-3f55e96423190575e5ec002ef36c0fadaaf0c469bc1e31faa0d3df335e2a7abc--H1pCXYcCzOxG (provision)
Unsachgemäßes Kurzschließen oder Durchtrennen von unter Spannung stehenden Leitungen und Kabeln ist lebensgefährlich.
- bib.al.original-language: en
- bib.dp.publication-date: 2018-06-29
- ids.document: 7104561
- ids.tracing: hash-3f55e96423190575e5ec002ef36c0fadaaf0c469bc1e31faa0d3df335e2a7abc
- obj.clause-number: 5.2.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-10cb2d03d6212224e4112dd3df6bf48c21c51cb38a7c9d91b79ffa95a519d241--RvoeFMbETGXc (provision)
Kurzschließen oder Durchtrennen von unter Spannung stehenden Leitungen und Kabeln als Notmaßnahme darf daher nur bei Gefährdung von Menschenleben und nur von Elektrofachkräften durchgeführt werden.
- bib.al.original-language: en
- bib.dp.publication-date: 2018-06-29
- ids.document: 7104561
- ids.tracing: hash-10cb2d03d6212224e4112dd3df6bf48c21c51cb38a7c9d91b79ffa95a519d241
- obj.clause-number: 5.2.3
- obj.element-name: paragraph
- obj.language: de
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

#### R195: 5.2.4 (heading)
- bib.al.original-language: en
- bib.dp.publication-date: 2018-06-29
- ids.document: 7104561
- obj.element-name: heading
- obj.language: de
- obj.specobject-type: heading

##### tr--hash-d3ab28877c2a7f3b5efbcad843573427927539773a10e5e3a7855f03760248b3--9wWOdGEwrbHY (provision)
Bei Annäherung (z. B. beim Erkunden und Retten) an unter Spannung stehende Niederspannungsanlagenteile ist der Mindestabstand nach Tabelle 2 einzuhalten.
- bib.al.original-language: en
- bib.dp.publication-date: 2018-06-29
- ids.document: 7104561
- ids.tracing: hash-d3ab28877c2a7f3b5efbcad843573427927539773a10e5e3a7855f03760248b3
- obj.clause-number: 5.2.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> tr--8e9b9d1a-8157-4b81-a49d-2d500c597b66--8nilfDyyzJnb

##### tr--hash-a0457d135e54b8203615581ced8b2d69c79adcf1ff7317b42dcd813949ff98d0--ADdNhVzpDArL (provision)
Dieser Abstand ist nicht erforderlich, wenn diese elektrischen Anlagenteile in frei zugänglichen Räumen offensichtlich unbeschädigt sind (z. B. Abstand zu Lichtschaltern und Steckdosen).
- bib.al.original-language: en
- bib.dp.publication-date: 2018-06-29
- ids.document: 7104561
- ids.tracing: hash-a0457d135e54b8203615581ced8b2d69c79adcf1ff7317b42dcd813949ff98d0
- obj.clause-number: 5.2.4
- obj.element-name: paragraph
- obj.language: de
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

##### tr--8e9b9d1a-8157-4b81-a49d-2d500c597b66--8nilfDyyzJnb: Zulässige Annäherungen in Niederspannungsanlagen (provision)
Tabelle 2 — Zulässige Annäherungen in Niederspannungsanlagen
| Nennspannung | Annäherung |
| --- | --- |
| bis AC 1 000 V oder DC 1 500 V | 1 m |
- bib.al.original-language: en
- bib.dp.publication-date: 2018-06-29
- ids.document: 7104561
- ids.tracing: hash-744616b664f143c4d1e3fc18fba8916d5ad6241608444b3ba75d43f5aae9515e
- obj.clause-number: Tabelle 2
- obj.element-name: table
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-a3cd19028cde5160fcbf0dc84644bc99165bb53797727443a077b675817c4dc8--3HpNUdKQjGx8 (provision)
Bei Löscharbeiten gelten die Mindestabstände nach den Tabellen 5 bis 8.
- bib.al.original-language: en
- bib.dp.publication-date: 2018-06-29
- ids.document: 7104561
- ids.tracing: hash-a3cd19028cde5160fcbf0dc84644bc99165bb53797727443a077b675817c4dc8
- obj.clause-number: 5.2.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> tr--8e9b9d1a-8157-4b81-a49d-2d500c597b66--QbpMeOdd24Rx

### R200: Besondere Maßnahmen für Hochspannungsanlagen (heading)
- bib.al.original-language: en
- bib.dp.publication-date: 2018-06-29
- ids.document: 7104561
- obj.clause-number: 5.3
- obj.element-name: heading
- obj.language: de
- obj.specobject-type: heading
- ChapterName: 5.3 Besondere Maßnahmen für Hochspannungsanlagen

#### R201: 5.3.1 (heading)
- bib.al.original-language: en
- bib.dp.publication-date: 2018-06-29
- ids.document: 7104561
- obj.element-name: heading
- obj.language: de
- obj.specobject-type: heading

##### tr--hash-ac69fd185bc136b27af70153c16e6cb77fad3f83dce5b981ec941dedf58e3bb7--2fs7axJhTlGY (provision)
Hochspannungsanlagen in abgeschlossenen elektrischen Betriebsstätten, wie z. B. Schalt- und Umspannanlagen, dürfen nur in Gegenwart einer für den Betrieb dieser Anlage verantwortlichen Person und nur von unmittelbar Beteiligten betreten werden.
- bib.al.original-language: en
- bib.dp.publication-date: 2018-06-29
- ids.document: 7104561
- ids.tracing: hash-ac69fd185bc136b27af70153c16e6cb77fad3f83dce5b981ec941dedf58e3bb7
- obj.clause-number: 5.3.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-60ffccee19aa4576134428757919706ac25ded7f22dd412e022c0038f98a29a0--yVUB8EwrL9Qt (provision)
Zur Rettung von Menschenleben ist das Betreten auch bei Abwesenheit dieser Person möglich, wenn eine Elektrofachkraft anwesend ist, die über spezielle Kenntnisse für Hochspannungsanlagen der entsprechenden Spannungsebene verfügt.
- bib.al.original-language: en
- bib.dp.publication-date: 2018-06-29
- ids.document: 7104561
- ids.tracing: hash-60ffccee19aa4576134428757919706ac25ded7f22dd412e022c0038f98a29a0
- obj.clause-number: 5.3.1
- obj.element-name: paragraph
- obj.language: de
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-8e2f1338dcb3e3ae6e072ec7409537555f7de93129a3a85087a852130df57118--I8dZl8J2Glop (provision)
Für im unmittelbaren Einflussbereich eines Brandes liegende Anlagenteile ist – wegen der Gefahr von Lichtbogenkurzschlüssen durch leitfähige Beläge, Ionisation usw. – vor Annäherung der spannungsfreie Zustand herzustellen und sicherzustellen [siehe DIN VDE 0105-100 (VDE 0105-100):2015-10, 6.2] .
- bib.al.original-language: en
- bib.dp.publication-date: 2018-06-29
- ids.document: 7104561
- ids.tracing: hash-8e2f1338dcb3e3ae6e072ec7409537555f7de93129a3a85087a852130df57118
- obj.clause-number: 5.3.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### R205: 5.3.2 (heading)
- bib.al.original-language: en
- bib.dp.publication-date: 2018-06-29
- ids.document: 7104561
- obj.element-name: heading
- obj.language: de
- obj.specobject-type: heading

##### tr--hash-4a690db93418756a389b98a40956ea83544386de4f09f412dcf8290df1e45452--eks2VJ4Bc5TM (provision)
Schalthandlungen in Hochspannungsanlagen dürfen nur durch den Anlagenverantwortlichen veranlasst werden.
- bib.al.original-language: en
- bib.dp.publication-date: 2018-06-29
- ids.document: 7104561
- ids.tracing: hash-4a690db93418756a389b98a40956ea83544386de4f09f412dcf8290df1e45452
- obj.clause-number: 5.3.2
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### R207: 5.3.3 (heading)
- bib.al.original-language: en
- bib.dp.publication-date: 2018-06-29
- ids.document: 7104561
- obj.element-name: heading
- obj.language: de
- obj.specobject-type: heading

##### tr--hash-7390c44fe95faa11f864736dd1b5a8528d803e975b4619eac17101114b9dd27b--2MCTctmqEek8 (provision)
Hochspannungsanlagen, z. B. Freileitungen, dürfen unter keinen Umständen durch behelfsmäßiges Erden und Kurzschließen oder Durchtrennen spannungsfrei gemacht werden, weil diese Maßnahmen mit nicht überschaubaren Gefahren verbunden sind.
- bib.al.original-language: en
- bib.dp.publication-date: 2018-06-29
- ids.document: 7104561
- ids.tracing: hash-7390c44fe95faa11f864736dd1b5a8528d803e975b4619eac17101114b9dd27b
- obj.clause-number: 5.3.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### R209: 5.3.4 (heading)
- bib.al.original-language: en
- bib.dp.publication-date: 2018-06-29
- ids.document: 7104561
- obj.element-name: heading
- obj.language: de
- obj.specobject-type: heading

##### tr--hash-d03ac495ff1e67a3c08d6c7e359d5970fb39737445f6af1ebd9758ed35c2ff69--CBqEExQQDhW3 (provision)
Bei Annäherung (z. B. beim Erkunden und Retten) an unter Spannung stehende Hochspannungsanlagen in nicht abgeschlossenen elektrischen Betriebsstätten, z. B. Freileitungen, sind die Mindestabstände nach Tabelle 3 einzuhalten.
- bib.al.original-language: en
- bib.dp.publication-date: 2018-06-29
- ids.document: 7104561
- ids.tracing: hash-d03ac495ff1e67a3c08d6c7e359d5970fb39737445f6af1ebd9758ed35c2ff69
- obj.clause-number: 5.3.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> tr--8e9b9d1a-8157-4b81-a49d-2d500c597b66--aUIWOAbngFpk

##### tr--hash-51c497a73d2044b3fccac47e972540c40ac62b0bd8525fdb7dcaa81bc7e64086--Nk0a9kYTWXI3 (provision)
Bei Unterschreiten dieser Mindestabstände besteht Lebensgefahr.
- bib.al.original-language: en
- bib.dp.publication-date: 2018-06-29
- ids.document: 7104561
- ids.tracing: hash-51c497a73d2044b3fccac47e972540c40ac62b0bd8525fdb7dcaa81bc7e64086
- obj.clause-number: 5.3.4
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--8e9b9d1a-8157-4b81-a49d-2d500c597b66--aUIWOAbngFpk: Zulässige Annäherungen in Hochspannungsanlagen (provision)
Tabelle 3 — Zulässige Annäherungen in Hochspannungsanlagen
| Nennspannung | Annäherung |
| --- | --- |
| bis 110 kV | 3 m |
| über 110 kV bis 220 kV | 4 m |
| über 220 kV bis 380 kV | 5 m |
- bib.al.original-language: en
- bib.dp.publication-date: 2018-06-29
- ids.document: 7104561
- ids.tracing: hash-75550db5120ff95e886cbae6f1351ee06215a78a0c3d332f83262b4ba43f2ed9
- obj.clause-number: Tabelle 3
- obj.element-name: table
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-b3d8346bf03491160637028e4afe02e3f8924cd9cc1286b2849589c65912c000--VM5cw1eKXNya (provision)
Unter Aufsicht von Elektrofachkräften oder elektrotechnisch unterwiesenen Personen ist eine Annäherung bis auf die Werte nach DIN VDE 0105-100 (VDE 0105-100):2015-10, Tabelle 102 möglich.
- bib.al.original-language: en
- bib.dp.publication-date: 2018-06-29
- ids.document: 7104561
- ids.tracing: hash-b3d8346bf03491160637028e4afe02e3f8924cd9cc1286b2849589c65912c000
- obj.clause-number: 5.3.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-07bd69f54c677236926b7b309f87f4558f2cec2c049283a67aa5a8210c70a7c2--DmN3gaUNzfan (provision)
Bei Rettungsarbeiten an Oberleitungen elektrischer Bahnen (bis 25 kV) ist eine Annäherung bis auf 1,5 m möglich [siehe DIN VDE 0105-103 (VDE 0105-103):2014-10, 6.4 .302].
- bib.al.original-language: en
- bib.dp.publication-date: 2018-06-29
- ids.document: 7104561
- ids.tracing: hash-07bd69f54c677236926b7b309f87f4558f2cec2c049283a67aa5a8210c70a7c2
- obj.clause-number: 5.3.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-21c8737aeda92890910106244df1c9acff7002172437db0c91dc358303a1e7e8--CeoR5JAUQoUP (provision)
Bei Löscharbeiten gelten die Mindestabstände nach den Tabellen 5 bis 8.
- bib.al.original-language: en
- bib.dp.publication-date: 2018-06-29
- ids.document: 7104561
- ids.tracing: hash-21c8737aeda92890910106244df1c9acff7002172437db0c91dc358303a1e7e8
- obj.clause-number: 5.3.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> tr--8e9b9d1a-8157-4b81-a49d-2d500c597b66--QbpMeOdd24Rx

#### R216: 5.3.5 (heading)
- bib.al.original-language: en
- bib.dp.publication-date: 2018-06-29
- ids.document: 7104561
- obj.element-name: heading
- obj.language: de
- obj.specobject-type: heading

##### tr--hash-3187122293dd2932131feb29a058e3d4ad7fc6ccb9d2fbd439190c957993bdbc--O5heo5IXSZRQ (provision)
Freileitungen und Fahrleitungen in der Nähe von Einsatzstellen können beschädigt werden und herunterfallen.
- bib.al.original-language: en
- bib.dp.publication-date: 2018-06-29
- ids.document: 7104561
- ids.tracing: hash-3187122293dd2932131feb29a058e3d4ad7fc6ccb9d2fbd439190c957993bdbc
- obj.clause-number: 5.3.5
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-b5378bc296aa3ac9aa7787f3faf1884c024c3c07cac17110f885b4296403f50f--VZ2buvcgjdJs (provision)
Das Betreten der Umgebung von herabgefallenen, unter Spannung stehenden Leitungen ist lebensgefährlich (Schrittspannung, siehe Bild 1).
- bib.al.original-language: en
- bib.dp.publication-date: 2018-06-29
- ids.document: 7104561
- ids.tracing: hash-b5378bc296aa3ac9aa7787f3faf1884c024c3c07cac17110f885b4296403f50f
- obj.clause-number: 5.3.5
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> tr--8e9b9d1a-8157-4b81-a49d-2d500c597b66--Arkb5LhWnZ8f

##### tr--8e9b9d1a-8157-4b81-a49d-2d500c597b66--Arkb5LhWnZ8f (provision)
Bild 1 — SchrittspannungU _S im Bereich einer Fehlerstelle bei der Schrittlänge l _S
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| Legende |  |
| --- | --- |
| U _S1 | Schrittspannung 1 |
| U _S2 | Schrittspannung 2 |
| l _S | Schrittlänge |
| Legende |  |
| --- | --- |
| U _S1 | Schrittspannung 1 |
| U _S2 | Schrittspannung 2 |
| l _S | Schrittlänge |
- bib.al.original-language: en
- bib.dp.publication-date: 2018-06-29
- ids.document: 7104561
- ids.tracing: hash-6794393bd5cbb216c0e2db82e735a0c63ae0aa1a056628e7ad5c976c6434f792
- obj.clause-number: 5.3.5
- obj.element-name: figure
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-a9ea51d1d9892eb594030263ee232e1c42d64f84f44b4ebdf75f11d31878ffc6--RCIUsC9Kyyi7 (provision)
Von der am Boden liegenden Freileitung ist daher ein Abstand von mindestens 20 m, von der am Boden liegenden Fahrleitung ein Abstand von 10 m einzuhalten.
- bib.al.original-language: en
- bib.dp.publication-date: 2018-06-29
- ids.document: 7104561
- ids.tracing: hash-a9ea51d1d9892eb594030263ee232e1c42d64f84f44b4ebdf75f11d31878ffc6
- obj.clause-number: 5.3.5
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-4c50ee17b605409c5ea6036620b67f6cdffd3b8fc6e9308b7d7d0e05de6ff9a2--KnMuR8RaTkaU (provision)
Hat die betreffende Leitung Berührung mit Metallteilen wie Zäunen, Geländern, Schienen usw., so ist von diesen Teilen ebenfalls der entsprechende Abstand einzuhalten.
- bib.al.original-language: en
- bib.dp.publication-date: 2018-06-29
- ids.document: 7104561
- ids.tracing: hash-4c50ee17b605409c5ea6036620b67f6cdffd3b8fc6e9308b7d7d0e05de6ff9a2
- obj.clause-number: 5.3.5
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-7922112b0455889c8e415d4622976fabb27ec107fa197b0c8452b2ffe3f2358e--23y6RKBnKEzS (provision)
Die Gefahrenzone ist abzusperren.
- bib.al.original-language: en
- bib.dp.publication-date: 2018-06-29
- ids.document: 7104561
- ids.tracing: hash-7922112b0455889c8e415d4622976fabb27ec107fa197b0c8452b2ffe3f2358e
- obj.clause-number: 5.3.5
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-ed3c54628c98c12d1b31fe7d77c915257d4929a0474dc23c074fc7894ca92304--43swbqMVtumY (provision)
Der Bereich darf erst wieder nach Beseitigung der Gefahr und Freigabe durch den Anlagenbetreiber betreten werden.
- bib.al.original-language: en
- bib.dp.publication-date: 2018-06-29
- ids.document: 7104561
- ids.tracing: hash-ed3c54628c98c12d1b31fe7d77c915257d4929a0474dc23c074fc7894ca92304
- obj.clause-number: 5.3.5
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### tr--8e9b9d1a-8157-4b81-a49d-2d500c597b66--tN52oWmteCvs: , Note (provision)
ANMERKUNG:
Mit den vorstehenden Abständen soll sichergestellt werden, dass selbst bei ungünstigen Bedingungen keine Gefährdung für die Einsatzkräfte vorliegt. Ungünstige Bedingungen liegen z. B. bei gelöschten 110-kV-Netzen und gleichzeitig hohen spezifischen Erdwiderständen vor.
- bib.al.original-language: en
- bib.dp.publication-date: 2018-06-29
- ids.document: 7104561
- ids.tracing: hash-9fb9b32c53d9b11479734a3a717e88b2c122dce85820d51afea14557b53272de
- obj.clause-number: 5.3.5
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### tr--hash-df397eb88ff027f1d8d5ae75a07ede4ad898263deddbdd49d1f8e4c5bb38ec22--t9SEgw5zDkzT (provision)
Jedoch kann eine Elektrofachkraft des betreffenden Anlagenbetreibers des Elektrizitätsversorgungsnetzes, die beurteilen kann, um welche Netzspannungsebene und Art der Sternpunkterdung es sich handelt, vor Ort den Einsatzkräften empfehlen, auf welchen Wert der Schutzabstand gegebenenfalls unter 20 m verringert werden kann.
- bib.al.original-language: en
- bib.dp.publication-date: 2018-06-29
- ids.document: 7104561
- ids.tracing: hash-df397eb88ff027f1d8d5ae75a07ede4ad898263deddbdd49d1f8e4c5bb38ec22
- obj.clause-number: 5.3.5
- obj.element-name: paragraph
- obj.language: de
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

##### tr--hash-7cd11ce12fdd2431db22e1ec2fbc9210d31fa1c2eff8298387f975b41b60b96d--YPGB4LEK8EDC (provision)
Dabei kann in Betracht gezogen werden, dass z. B.:
- in Niederspannungsnetzen keine gefahrbringenden Schrittspannungen vorkommen;
- im Hochspannungsbereich bis 30 kV (Mittelspannungsbereich) der Schutzabstand auf bis zu 10 m reduziert werden kann;
- bei den Spannungsebenen 220 kV und 380 kV die Sternpunkte grundsätzlich niederohmig geerdet sind und ein Erdschluss daher in kurzer Zeit abgeschaltet wird; das Gleiche gilt auch für niederohmig geerdete 110-kV-Netze;
- in gelöschten 110-kV-Netzen und gleichzeitig hohen spezifischen Erdwiderständen eine Reduzierung des Schutzabstandes unter 20 m nicht empfohlen wird.
- bib.al.original-language: en
- bib.dp.publication-date: 2018-06-29
- ids.document: 7104561
- ids.tracing: hash-7cd11ce12fdd2431db22e1ec2fbc9210d31fa1c2eff8298387f975b41b60b96d
- obj.clause-number: 5.3.5
- obj.element-name: paragraph
- obj.language: de
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

##### tr--hash-d3fa1e1c43169bc726011b9527d6658030ca8c61a0c89adcd3a55fd7fcde34b3--3tfGNXX4EJQP (provision)
Den Angaben für den Schutzabstand liegen die Annahmen eines spezifischen Erdwiderstandes von 1 000 Ωm, eines Erdschlussreststromes von 132 A sowie einer maximalen Schrittspannung von 75 V zugrunde.
- bib.al.original-language: en
- bib.dp.publication-date: 2018-06-29
- ids.document: 7104561
- ids.tracing: hash-d3fa1e1c43169bc726011b9527d6658030ca8c61a0c89adcd3a55fd7fcde34b3
- obj.clause-number: 5.3.5
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### R228: Besondere Maßnahmen für Anlagen mit starken Magnetfeldern – supraleitende Magnete (heading)
- bib.al.original-language: en
- bib.dp.publication-date: 2018-06-29
- ids.document: 7104561
- obj.clause-number: 5.4
- obj.element-name: heading
- obj.language: de
- obj.specobject-type: heading
- ChapterName: 5.4 Besondere Maßnahmen für Anlagen mit starken Magnetfeldern – supraleitende Magnete

#### R229: Magnetische Supraleiter und deren Anwendungen (heading)
- bib.al.original-language: en
- bib.dp.publication-date: 2018-06-29
- ids.document: 7104561
- obj.clause-number: 5.4.1
- obj.element-name: heading
- obj.language: de
- obj.specobject-type: heading
- ChapterName: 5.4.1 Magnetische Supraleiter und deren Anwendungen

##### R230: Allgemeines (heading)
- bib.al.original-language: en
- bib.dp.publication-date: 2018-06-29
- ids.document: 7104561
- obj.clause-number: 5.4.1.1
- obj.element-name: heading
- obj.language: de
- obj.specobject-type: heading
- ChapterName: 5.4.1.1 Allgemeines

###### tr--hash-e6a53857c4ae8fbf5ac7505013eda4a014eb75cd38ff50a8dea8f20bb6a470e5--sXJd1RrikiYT: Allgemeines (provision)
Supraleitende Magnete werden
- in Forschungseinrichtungen (bis zu 20 Tesla) und
- vor allem im medizinischen Bereich der Kernspintomographen bzw. Magnetresonanztomographen (MRT) mit 0,5 Tesla bis 7 Tesla
verwendet.
- bib.al.original-language: en
- bib.dp.publication-date: 2018-06-29
- ids.document: 7104561
- ids.tracing: hash-e6a53857c4ae8fbf5ac7505013eda4a014eb75cd38ff50a8dea8f20bb6a470e5
- obj.clause-number: 5.4.1.1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### tr--8e9b9d1a-8157-4b81-a49d-2d500c597b66--aBMMUP8x9jpQ: Allgemeines, Note (provision)
ANMERKUNG 1:
Supraleitende Magnete werden auch als elektrische Energiespeicher und als Kurzschlussstrombegrenzer in Hochspannungsnetzen eingesetzt (z. B. Hochspannungsgleichstromübertragung – HGÜ).
- bib.al.original-language: en
- bib.dp.publication-date: 2018-06-29
- ids.document: 7104561
- ids.tracing: hash-6437358b71fa96629428d572690ddc8bf95964040307e716c0983d2627d6f4f6
- obj.clause-number: 5.4.1.1
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### tr--8e9b9d1a-8157-4b81-a49d-2d500c597b66--ktpXq3Exj3Gd: Allgemeines, Note (provision)
ANMERKUNG 2:
Ein Tesla entspricht der 10 000-fachen Stärke des Erdmagnetfeldes.
- bib.al.original-language: en
- bib.dp.publication-date: 2018-06-29
- ids.document: 7104561
- ids.tracing: hash-0a624e1c63bb95603911f826fd6ab45664cb5a68defd4acc7fb94b30c6e70573
- obj.clause-number: 5.4.1.1
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### R234: Gefährdungen (heading)
- bib.al.original-language: en
- bib.dp.publication-date: 2018-06-29
- ids.document: 7104561
- obj.clause-number: 5.4.1.2
- obj.element-name: heading
- obj.language: de
- obj.specobject-type: heading
- ChapterName: 5.4.1.2 Gefährdungen

###### tr--hash-de2e09573aba620e00b02813a93aa26b867cbb0af25fb82dd113591f54e944ff--ceWjBedXWEcT: Gefährdungen (provision)
Das Magnetfeld bei Supraleitern ist dauerhaft auch bei abgeschalteter Stromversorgung vorhanden.
- bib.al.original-language: en
- bib.dp.publication-date: 2018-06-29
- ids.document: 7104561
- ids.tracing: hash-de2e09573aba620e00b02813a93aa26b867cbb0af25fb82dd113591f54e944ff
- obj.clause-number: 5.4.1.2
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### tr--hash-23ed1189abc77d0da3018bb41d805ef50b6ef46554bbff6f3f4378b0da5ec838--e9cBxjs0hqpd: Gefährdungen (provision)
Sämtliche ferromagnetischen Teile können in das Magnetfeld gezogen werden.
- bib.al.original-language: en
- bib.dp.publication-date: 2018-06-29
- ids.document: 7104561
- ids.tracing: hash-23ed1189abc77d0da3018bb41d805ef50b6ef46554bbff6f3f4378b0da5ec838
- obj.clause-number: 5.4.1.2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### tr--hash-5004cd826f0ae79f857c44f4363c756bd49ffc0af57848856d0e5160cbde2728--PPIRHBHd4CU0: Gefährdungen (provision)
Eine besondere Gefährdung besteht für Einsatzkräfte mit ferromagnetischen Atemschutzflaschen.
- bib.al.original-language: en
- bib.dp.publication-date: 2018-06-29
- ids.document: 7104561
- ids.tracing: hash-5004cd826f0ae79f857c44f4363c756bd49ffc0af57848856d0e5160cbde2728
- obj.clause-number: 5.4.1.2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### tr--hash-052d39723826949cfc408ef3e6b536a78aa44bce87e5abb0b780096eed529b78--a7kw3vTcqIIA: Gefährdungen (provision)
Der Atemschutzgeräteträger kann unvermittelt in oder an den supraleitenden Magneten gezogen werden.
- bib.al.original-language: en
- bib.dp.publication-date: 2018-06-29
- ids.document: 7104561
- ids.tracing: hash-052d39723826949cfc408ef3e6b536a78aa44bce87e5abb0b780096eed529b78
- obj.clause-number: 5.4.1.2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### tr--hash-3df76fd33cd89b7495390b6490e4da75c443a7a2cb0cc0fe40c0bc806d982156--EkEad6VEXKzX: Gefährdungen (provision)
Auch können Ausrüstungsgegenstände, Werkzeuge, Feuerlöscher, Krankenbetten oder Ähnliches in oder an supraleitende Magnete gezogen werden.
- bib.al.original-language: en
- bib.dp.publication-date: 2018-06-29
- ids.document: 7104561
- ids.tracing: hash-3df76fd33cd89b7495390b6490e4da75c443a7a2cb0cc0fe40c0bc806d982156
- obj.clause-number: 5.4.1.2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### R240: Maßnahmen (heading)
- bib.al.original-language: en
- bib.dp.publication-date: 2018-06-29
- ids.document: 7104561
- obj.clause-number: 5.4.1.3
- obj.element-name: heading
- obj.language: de
- obj.specobject-type: heading
- ChapterName: 5.4.1.3 Maßnahmen

###### tr--hash-83191772120678ec423a3c9b7d1ff87b058bc9bbd24e9ea6b7a2be13521ba963--SMwfatOMeGxx: Maßnahmen (provision)
Nur die benötigten Einsatzkräfte dürfen den unmittelbaren Gefahrenbereich (in der Regel den betroffenen Raum) betreten.
- bib.al.original-language: en
- bib.dp.publication-date: 2018-06-29
- ids.document: 7104561
- ids.tracing: hash-83191772120678ec423a3c9b7d1ff87b058bc9bbd24e9ea6b7a2be13521ba963
- obj.clause-number: 5.4.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### tr--hash-0075d25135617ec49117273972ca59a05b75f09c10a9389f77467843a8a1a6bb--BcF7KhqxqKxK: Maßnahmen (provision)
Dabei sollten diese Einsatzkräfte den größtmöglichen Abstand halten.
- bib.al.original-language: en
- bib.dp.publication-date: 2018-06-29
- ids.document: 7104561
- ids.tracing: hash-0075d25135617ec49117273972ca59a05b75f09c10a9389f77467843a8a1a6bb
- obj.clause-number: 5.4.1.3
- obj.element-name: paragraph
- obj.language: de
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

###### tr--hash-9755caaa5dc570cb26e6c856fe6c84e63c86f184ba7559ed2fd903f59349f72d--j8pdIHsuaIah: Maßnahmen (provision)
Das Betreten von Räumen mit starken Magnetfeldern ist nur mit nicht ferromagnetischen Ausrüstungsgegenständen, z. B. Komposit-Atemschutzflaschen, zulässig.
- bib.al.original-language: en
- bib.dp.publication-date: 2018-06-29
- ids.document: 7104561
- ids.tracing: hash-9755caaa5dc570cb26e6c856fe6c84e63c86f184ba7559ed2fd903f59349f72d
- obj.clause-number: 5.4.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### tr--hash-e6100e99b85a171b84bcacc2ecee4db4bd1124ec5dbed53347b972b6bd2d8e84--DV1FpLXOyYvm: Maßnahmen (provision)
Zum Löschen von Entstehungsbränden dürfen nur nicht ferromagnetische Feuerlöscher verwendet werden (Handelsbegriff: „antimagnetisch“).
- bib.al.original-language: en
- bib.dp.publication-date: 2018-06-29
- ids.document: 7104561
- ids.tracing: hash-e6100e99b85a171b84bcacc2ecee4db4bd1124ec5dbed53347b972b6bd2d8e84
- obj.clause-number: 5.4.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### tr--hash-d40cd09ffcce7f092d54415706a32b821099bff58857c1dfacf2baef90a0ae77--MDKSun24fAYK: Maßnahmen (provision)
Eine schnelle Abschaltung des Magnetfeldes ist nur in Form einer Notabschaltung über ein Ablassen des Kühlmittels (in der Regel flüssiges Helium bei 4 K) möglich.
- bib.al.original-language: en
- bib.dp.publication-date: 2018-06-29
- ids.document: 7104561
- ids.tracing: hash-d40cd09ffcce7f092d54415706a32b821099bff58857c1dfacf2baef90a0ae77
- obj.clause-number: 5.4.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### tr--hash-e8f0f137d5434652d3a8582591b045ae3fde01f13408c0d2f0ef8d1cd6605294--t7p7HWGncMN9: Maßnahmen (provision)
Eine Notabschaltung des Magnetfeldes kann eine Gefährdung durch ausströmendes tiefkaltes Gas verursachen.
- bib.al.original-language: en
- bib.dp.publication-date: 2018-06-29
- ids.document: 7104561
- ids.tracing: hash-e8f0f137d5434652d3a8582591b045ae3fde01f13408c0d2f0ef8d1cd6605294
- obj.clause-number: 5.4.1.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### tr--hash-2a5e12f175d812eb31a13298c4b73a5408747e749c1ff7d4dd5feb9c91fe5a1e--aif98LmbjoZI: Maßnahmen (provision)
Die Notabschaltung der elektrischen Komponenten erfolgt über einen separaten Not-Aus-Schalter und hat keinen Einfluss auf das Magnetfeld.
- bib.al.original-language: en
- bib.dp.publication-date: 2018-06-29
- ids.document: 7104561
- ids.tracing: hash-2a5e12f175d812eb31a13298c4b73a5408747e749c1ff7d4dd5feb9c91fe5a1e
- obj.clause-number: 5.4.1.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### tr--hash-2dca8377a9aaa6dc05aea322e52be1049ee6ce1c2c60e45460b2fd99bb17f27d--FDPrHLpfbZ1W: Maßnahmen (provision)
Abschaltungen sind, außer bei Lebensgefahr, zuvor mit dem Anlagenbetreiber abzusprechen.
- bib.al.original-language: en
- bib.dp.publication-date: 2018-06-29
- ids.document: 7104561
- ids.tracing: hash-2dca8377a9aaa6dc05aea322e52be1049ee6ce1c2c60e45460b2fd99bb17f27d
- obj.clause-number: 5.4.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### tr--8e9b9d1a-8157-4b81-a49d-2d500c597b66--KYFzlMsalzNj: Maßnahmen, Note (provision)
ANMERKUNG:
Eine Notabschaltung verursacht sehr hohe Kosten und kann zu einer Beschädigung oder Zerstörung des Magneten führen.
- bib.al.original-language: en
- bib.dp.publication-date: 2018-06-29
- ids.document: 7104561
- ids.tracing: hash-b8059cec67cd32663b6ec960d883e7bb545db3cb2e3e33d96068add56eefe88e
- obj.clause-number: 5.4.1.3
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

## R250: Eignung von Löschmitteln (heading)
- bib.al.original-language: en
- bib.dp.publication-date: 2018-06-29
- ids.document: 7104561
- obj.clause-number: 6
- obj.element-name: heading
- obj.language: de
- obj.specobject-type: heading
- ChapterName: 6 Eignung von Löschmitteln

### R251: Auswahl der Löschmittel (heading)
- bib.al.original-language: en
- bib.dp.publication-date: 2018-06-29
- ids.document: 7104561
- obj.clause-number: 6.1
- obj.element-name: heading
- obj.language: de
- obj.specobject-type: heading
- ChapterName: 6.1 Auswahl der Löschmittel

#### tr--hash-da6d229225bb11ed0921859554969da49fdb531809f9e21f0f8b8a03c411f0b1--9Z7kbWyimFOz: Auswahl der Löschmittel (provision)
Als Löschmittel können z. B. eingesetzt werden:
- Wasser;
- Schaum;
- Pulver;
- Kohlenstoffdioxid.
- bib.al.original-language: en
- bib.dp.publication-date: 2018-06-29
- ids.document: 7104561
- ids.tracing: hash-da6d229225bb11ed0921859554969da49fdb531809f9e21f0f8b8a03c411f0b1
- obj.clause-number: 6.1
- obj.element-name: paragraph
- obj.language: de
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-1ca0902abb39b723b575144e1a96ad4f3c69965ed471a3f2c787fb5c14b0f040--6z2MqcrAXDVs: Auswahl der Löschmittel (provision)
Diese Löschmittel sind unter Beachtung ihrer Eignung und eventueller Einsatzbeschränkungen auszuwählen.
- bib.al.original-language: en
- bib.dp.publication-date: 2018-06-29
- ids.document: 7104561
- ids.tracing: hash-1ca0902abb39b723b575144e1a96ad4f3c69965ed471a3f2c787fb5c14b0f040
- obj.clause-number: 6.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### R254: Anwendung von Löschmitteln (heading)
- bib.al.original-language: en
- bib.dp.publication-date: 2018-06-29
- ids.document: 7104561
- obj.clause-number: 6.2
- obj.element-name: heading
- obj.language: de
- obj.specobject-type: heading
- ChapterName: 6.2 Anwendung von Löschmitteln

#### R255: Allgemeines (heading)
- bib.al.original-language: en
- bib.dp.publication-date: 2018-06-29
- ids.document: 7104561
- obj.clause-number: 6.2.1
- obj.element-name: heading
- obj.language: de
- obj.specobject-type: heading
- ChapterName: 6.2.1 Allgemeines

##### tr--hash-bde40f3be5ac3111c0354de0219f454c04a49c20866a9f82611544f36ae15185--ZXNMvetPTpuY: Allgemeines (provision)
Die in den Tabellen 5 bis 8 genannten Mindestabstände zwischen Löschmittelaustrittsöffnung und unter Spannung stehenden Teilen der elektrischen Anlagen sind erforderlich, um Stromeinwirkungen auf das den Löscheinsatz durchführende Personal zu verhindern.
- bib.al.original-language: en
- bib.dp.publication-date: 2018-06-29
- ids.document: 7104561
- ids.tracing: hash-bde40f3be5ac3111c0354de0219f454c04a49c20866a9f82611544f36ae15185
- obj.clause-number: 6.2.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> tr--8e9b9d1a-8157-4b81-a49d-2d500c597b66--QbpMeOdd24Rx

##### tr--hash-586bf695bc73640fc39639222cb2f36f596006e76413f08e2f1a881d0fd7f422--x9FdUtArS2QK: Allgemeines (provision)
Dabei ist nicht nur die Gefährdung durch den elektrischen Strom, sondern auch die Gefährdung durch reflexartige Handlungen zu verhindern.
- bib.al.original-language: en
- bib.dp.publication-date: 2018-06-29
- ids.document: 7104561
- ids.tracing: hash-586bf695bc73640fc39639222cb2f36f596006e76413f08e2f1a881d0fd7f422
- obj.clause-number: 6.2.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-c22b8224ec2e1447f7400cbae3e5f516fc77cc17e4f2ff7ce10745e7770e8b4f--CmUKLDlSs0li: Allgemeines (provision)
Das ist gegeben, wenn der Stromfluss über den menschlichen Körper nicht wahrnehmbar ist.
- bib.al.original-language: en
- bib.dp.publication-date: 2018-06-29
- ids.document: 7104561
- ids.tracing: hash-c22b8224ec2e1447f7400cbae3e5f516fc77cc17e4f2ff7ce10745e7770e8b4f
- obj.clause-number: 6.2.1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-d19e42648e1e1daaf664702c172c96f9336e45aa6259a6acba0c8a68efe20b38--GV5o68t8736q: Allgemeines (provision)
Bei Bränden in abgeschlossenen Betriebsstätten dürfen unter Spannung stehende Anlagenteile nur im Einvernehmen mit dem Anlagenverantwortlichen mit Wasser angespritzt werden.
- bib.al.original-language: en
- bib.dp.publication-date: 2018-06-29
- ids.document: 7104561
- ids.tracing: hash-d19e42648e1e1daaf664702c172c96f9336e45aa6259a6acba0c8a68efe20b38
- obj.clause-number: 6.2.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-ee75c944aab61efcbedcaf68277d6930513e487a1d003cbc613475492dc51133--s4GAGIBF2gvz: Allgemeines (provision)
Das Einvernehmen kann auch durch vorherige Absprache hergestellt werden.
- bib.al.original-language: en
- bib.dp.publication-date: 2018-06-29
- ids.document: 7104561
- ids.tracing: hash-ee75c944aab61efcbedcaf68277d6930513e487a1d003cbc613475492dc51133
- obj.clause-number: 6.2.1
- obj.element-name: paragraph
- obj.language: de
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

##### tr--hash-9d87c338abff27a3dc1365ec6f7c3d58970a4765c677f59c084450ec56f7b8bf--xVHA4pjw79zi: Allgemeines (provision)
Sind den Einsatzkräften die anstehenden Spannungen und die örtlichen Verhältnisse zunächst unbekannt, so dürfen beim Einsatz von Strahlrohren CM nach DIN 14365-1 zwischen Strahlrohr und unter Spannung stehenden Anlagenteilen die Richtwerte nach Tabelle 4 nicht unterschritten werden.
- bib.al.original-language: en
- bib.dp.publication-date: 2018-06-29
- ids.document: 7104561
- ids.tracing: hash-9d87c338abff27a3dc1365ec6f7c3d58970a4765c677f59c084450ec56f7b8bf
- obj.clause-number: 6.2.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> tr--8e9b9d1a-8157-4b81-a49d-2d500c597b66--OJ35a4X5fXHR

##### tr--hash-fb0c43000a50bfe356f3441817ac3f13102443c3ef660dc5aac5d877f32f3e3a--QSNFnamIJkOd: Allgemeines (provision)
Im Zweifelsfall ist immer der höchste Abstand einzuhalten.
- bib.al.original-language: en
- bib.dp.publication-date: 2018-06-29
- ids.document: 7104561
- ids.tracing: hash-fb0c43000a50bfe356f3441817ac3f13102443c3ef660dc5aac5d877f32f3e3a
- obj.clause-number: 6.2.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--8e9b9d1a-8157-4b81-a49d-2d500c597b66--OJ35a4X5fXHR: Richtwerte (provision)
Tabelle 4 — Richtwerte
| Strahlrohr DIN 14365-CM | Niederspannung (N) ≤ AC 1 kV oder ≤ DC 1,5 kV | Hochspannung (H) > AC 1 kV oder > DC 1,5 kV |
| --- | --- | --- |
| Sprühstrahl | 1 m | 5 m |
| Vollstrahl | 5 m | 10 m |
| Kurzzeichen | N-1-5 | H-5-10 |
- bib.al.original-language: en
- bib.dp.publication-date: 2018-06-29
- ids.document: 7104561
- ids.tracing: hash-73032ae86ed5ff012fd7b1d9cb1727d7262c5440265c65bf2adac931ca3c832d
- obj.clause-number: Tabelle 4
- obj.element-name: table
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-998b9b9164fc7b7da2ad32997199daefc0d2888d39a529e94aa546c0caab1c4e--tnLTZskz3Fkj: Allgemeines (provision)
In Niederspannungsanlagen gelten diese Richtwerte auch für Feuerlöscher nach DIN EN 3 (alle Teile) und in allen Anlagen auch für größere Wasserlöschgeräte, wenn deren Strahlrohre im Sinne der elektrischen Sicherheit DIN 14365-2:1986-09 entsprechen.
- bib.al.original-language: en
- bib.dp.publication-date: 2018-06-29
- ids.document: 7104561
- ids.tracing: hash-998b9b9164fc7b7da2ad32997199daefc0d2888d39a529e94aa546c0caab1c4e
- obj.clause-number: 6.2.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### tr--hash-af89a724fdeb69b6dab1e519ad5268678e1ca16694151c2dbbab0db88ea491ee--jVHW8FtshC2N: Allgemeines (provision)
Die Verwendungs- bzw. Warnhinweise auf den Löschgeräten sind zu beachten.
- bib.al.original-language: en
- bib.dp.publication-date: 2018-06-29
- ids.document: 7104561
- ids.tracing: hash-af89a724fdeb69b6dab1e519ad5268678e1ca16694151c2dbbab0db88ea491ee
- obj.clause-number: 6.2.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### R266: Wasser (heading)
- bib.al.original-language: en
- bib.dp.publication-date: 2018-06-29
- ids.document: 7104561
- obj.clause-number: 6.2.2
- obj.element-name: heading
- obj.language: de
- obj.specobject-type: heading
- ChapterName: 6.2.2 Wasser

##### tr--hash-db2b31f034ef31d1ab89e1ab56ab6242d6548e092a00065e4ab9fae92c565950--kpD9ut1k48aL: Wasser (provision)
Für den Einsatz von Wasser gilt Tabelle 5.
- bib.al.original-language: en
- bib.dp.publication-date: 2018-06-29
- ids.document: 7104561
- ids.tracing: hash-db2b31f034ef31d1ab89e1ab56ab6242d6548e092a00065e4ab9fae92c565950
- obj.clause-number: 6.2.2
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> tr--8e9b9d1a-8157-4b81-a49d-2d500c597b66--QbpMeOdd24Rx

##### tr--8e9b9d1a-8157-4b81-a49d-2d500c597b66--QbpMeOdd24Rx: Löschmittel Wassera (provision)
Tabelle 5 — Löschmittel Wasser^a
| Lfd. Nr. | Geräte/Anwendungsform | Wirksame Wurfweite (Mittelwert) m | Eignung für Brandklasse nach DIN EN 2 | Mindestabstände (m) zwischen Löschmittelaustrittsöffnung und unter Spannung stehenden Anlagenteilen |  |  |  |  |
| --- | --- | --- | --- | --- | --- | --- | --- | --- |
| Lfd. Nr. | Geräte/Anwendungsform | Wirksame Wurfweite (Mittelwert) m | Eignung für Brandklasse nach DIN EN 2 | Niederspannung bis | Hochspannung bis AC |  |  |  |
| Lfd. Nr. | Geräte/Anwendungsform | Wirksame Wurfweite (Mittelwert) m | Eignung für Brandklasse nach DIN EN 2 | AC 1 000 V oder DC 1 500 V | 30 kV | 110 kV | 220 kV | 380 kV |
|  | Strahlrohre CM nach DIN 14365-1:1991-02 |  |  |  |  |  |  |  |
| 1a | Sprühstrahl | 5 (bei 5 bar Fließdruck) | A B nur eingeschränkt | 1 | 3^b | 3 | 4 | 5 |
| 1b | Vollstrahl | 10 (bei 5 bar Fließdruck) | A | 5 | 5 | 6 | 7 | 8 |
|  | Strahlrohre nach DIN EN 15182-2 (≤ 235 l/min; C-Kupplung) |  |  |  | ^Eine Gefährdungsbeurteilung ist durchzuführen, ob eine elektrische Prüfung erforderlich ist ^c |  |  |  |
| 2a | Strahlrohre nach Sprühstrahl | 3 bis 5 | A B nur eingeschränkt | 1 | ^Eine Gefährdungsbeurteilung ist durchzuführen, ob eine elektrische Prüfung erforderlich ist ^c |  |  |  |
| 2b | Vollstrahl | > 10 | A | 5 | ^Eine Gefährdungsbeurteilung ist durchzuführen, ob eine elektrische Prüfung erforderlich ist ^c |  |  |  |
| 3 | Tragbare oder fahrbare Feuerlöscher, die die Anforderung nach DIN EN 3-7:2007-10, Abschnitt 9 erfüllen | 2 bis 6 | A bzw. A + B | 1 | ^d |  |  |  |
| 4 | Tragbare oder fahrbare Feuerlöscher, die die Anforderung nach DIN EN 3-7:2007-10, Abschnitt 9 nicht erfüllen | 2 bis 6 | A bzw. A + B | Einsatz nur in spannungsfreien Anlagenteilen | Einsatz nur in spannungsfreien Anlagenteilen |  |  |  |
| - a Bei tragbaren und fahrbaren Feuerlöschern: Wasser auch mit Zusätzen. - b Bei Aufsicht durch elektrotechnisch unterwiesene Personen oder Elektrofachkräfte ist ein Mindestabstand von 2 m zulässig. - c Da DIN EN 15182-1 bis DIN EN 15182-4 keine Angaben zur elektrischen Prüfung enthalten, hat der Unternehmer besondere Sorgfalt nach Betriebssicherheitsverordnung §3 (1) bzw. UVV Feuerwehr, DGUV Vorschrift 49, §29 (2) walten zu lassen. - d Feuerlöscher nach DIN EN 3 (alle Teile) können auch für Hochspannungsanlagen typgeprüft sein. Die Verwendungshinweise auf diesen Löschgeräten sind zu beachten. |  |  |  |  |  |  |  |  |
| Gefahrenhinweise/Einsatzbeschränkungen Brände im Bereich elektrischer Anlagen sollten möglichst mit Sprühstrahl bekämpft werden. Wird bei Strahlrohren CM nach DIN 14365-1 ein Fließdruck von 5 bar überschritten, sind die angegebenen Mindestabstände bei Einsatz in Hochspannungsanlagen um zusätzlich 2 m zu vergrößern. Ist im Sonderfall, der zwischen Anlagenbetreiber und Feuerwehr abzusprechen ist, die Verwendung von Strahlrohren BM nach DIN 14365-1:1991-02 nicht zu vermeiden, erhöhen sich die Mindestabstände: – bei Verwendung mit Mundstück um 5 m; – bei Verwendung ohne Mundstück um 10 m. Die angegebenen bzw. errechneten Mindestabstände gelten auch für andere Strahlrohre, für die mindestens eine gleichhohe elektrische Sicherheit wie nach DIN 14365-2:1986-09 nachgewiesen wurde. Zur Erreichung des Schutzziels nach 6.2.1 kann der Nachweis über erforderliche Mindestabstände auch mit anderen geeigneten Prüfungen erbracht werden. Bei Wasser mit Bestandteilen, welche die Leitfähigkeit erhöhen, wie z. B. Seewasser und dergleichen, ergeben sich keine Veränderungen der Mindestabstände, jedoch ist die Bildung von leitfähigen Überzügen auf Isolatoren möglich. Wasser mit Bestandteilen, welche die Strahleigenschaft verändern, z. B. Netzmittel, darf im Bereich unter Spannung stehender elektrischer Anlagen nur eingesetzt werden, wenn die einzuhaltenden Mindestabstände in Anlehnung an DIN 14365-2:1986-09 als vorbereitende Maßnahme (siehe Abschnitt 4) für diese Anlagen ermittelt worden sind. Sonstige Geräte, wie z. B. Wasserwerfer, Sonderlöscher, dürfen im Bereich unter Spannung stehender elektrischer Anlagen nur eingesetzt werden, wenn die einzuhaltenden Mindestabstände in Anlehnung an DIN 14365-2:1986-09 als vorbereitende Maßnahme (siehe Abschnitt 4) für diese Anlagen ermittelt worden sind. |  |  |  |  |  |  |  |  |
- bib.al.original-language: en
- bib.dp.publication-date: 2018-06-29
- ids.document: 7104561
- ids.tracing: hash-2eae3746838f367c2af20eba812196fc5414af73b4189456d246398530d9b521
- obj.clause-number: Tabelle 5
- obj.element-name: table
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R255
- cross-reference -> R108

###### tr--8e9b9d1a-8157-4b81-a49d-2d500c597b66--sBHgbfCirrjD: Wasser, Note (provision)
ANMERKUNG:
Siehe Anhang B „Erläuterungen“.
- bib.al.original-language: en
- bib.dp.publication-date: 2018-06-29
- ids.document: 7104561
- ids.tracing: hash-baceacd472f83bb3307f19ab73e25b150c1fdc48c39f90126a9af7f9596fa089
- obj.clause-number: 6.2.2
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> R318

#### R270: Schaum (heading)
- bib.al.original-language: en
- bib.dp.publication-date: 2018-06-29
- ids.document: 7104561
- obj.clause-number: 6.2.3
- obj.element-name: heading
- obj.language: de
- obj.specobject-type: heading
- ChapterName: 6.2.3 Schaum

##### tr--hash-55f52d2128305c5832e3859e2790d35bedc3a96ad49fd802a70fd1b954e32b39--FqjsHG1zepZs: Schaum (provision)
Für den Einsatz von Schaum gilt Tabelle 6.
- bib.al.original-language: en
- bib.dp.publication-date: 2018-06-29
- ids.document: 7104561
- ids.tracing: hash-55f52d2128305c5832e3859e2790d35bedc3a96ad49fd802a70fd1b954e32b39
- obj.clause-number: 6.2.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> tr--8e9b9d1a-8157-4b81-a49d-2d500c597b66--wIDF0tZG2zG5

##### tr--8e9b9d1a-8157-4b81-a49d-2d500c597b66--wIDF0tZG2zG5: Löschschaum nach DIN EN 1568 (alle Teile) (provision)
Tabelle 6 — Löschschaum nach DIN EN 1568 (alle Teile)
| Lfd.Nr. | Geräte/ Anwendungsform | Wirksame Wurfweite (Mittelwert) m | Eignung für Brandklasse nach DIN EN 2^a | Mindestabstände (m) zwischen Löschmittelaustrittsöffnung und unter Spannung stehenden Anlagenteilen |  |  |  |  |
| --- | --- | --- | --- | --- | --- | --- | --- | --- |
| Lfd.Nr. | Geräte/ Anwendungsform | Wirksame Wurfweite (Mittelwert) m | Eignung für Brandklasse nach DIN EN 2^a | Niederspannung bis | Hochspannung bis AC |  |  |  |
| Lfd.Nr. | Geräte/ Anwendungsform | Wirksame Wurfweite (Mittelwert) m | Eignung für Brandklasse nach DIN EN 2^a | AC 1 000 V oder DC 1 500 V | 30 kV | 110 kV | 220 kV | 380 kV |
| 1 | Tragbare oder fahrbare Feuerlöscher, die die Anforderungen nach DIN EN 3-7:2007-10, Abschnitt 9 erfüllen | 2 bis 6 | A, B | 1 |  |  |  |  |
| 2 | Tragbare oder fahrbare Feuerlöscher, die die Anforderungen nach DIN EN 3-7:2007-10, Abschnitt 9 nicht erfüllen | 2 bis 6 | A, B |  | Einsatz nur in spannungsfreien Anlagenteilen |  |  |  |
| 3 | Sonstige Geräte, z. B. typgeprüfte tragbare Feuerlöscher oder typgeprüfte fahrbare Feuerlöscher | 3 bis 7 | A, B | 3^b |  |  |  |  |
| 4 | Tragbare Schaumstrahlrohre nach DIN EN 16712-3:2015-12 S1/S2/S4/S8 M0,5/M1/M2/M4/M8 | 9/12/20/25 3/4/6/7/10 | A, B A, B |  |  |  |  |  |
| 5 | Schaumstrahlrohre für Werfer-Unterteile nach DIN 14366-2:1984-10 SW10/SW20/SW40 | 35/45/65 | A, B |  |  |  |  |  |
|  | Bei Abgabe von Druckluftschaum: Strahlrohre nach DIN 14365-1:1991-02 oder DIN EN 15182 oder andere Strahlrohre mit Austrittsöffnungen ≤ 25 mm Durchmesser (für alle Strahlrohre gilt: ≤ 235 l/min Wasser-Schaummittelgemisch und C-Kupplung) |  | A, B |  |  |  |  |  |
| 6a | Sprühstrahl | 3 bis 5 |  | 1 |  |  |  |  |
| 6b | Vollstrahl | > 10 |  | 5 |  |  |  |  |
| ^a Die Eignung kann auch die Brandklasse F umfassen. ^b Dies gilt nur für den Einsatz typgeprüfter Löschgeräte und deren Verwendung in elektrischen Anlagen. |  |  |  |  |  |  |  |  |
| Gefahrenhinweise/Einsatzbeschränkungen Eine Gefahr besteht, wenn zwischen der Einsatzkraft und einem unter Spannung stehenden Anlagenteil eine durchgehende Verbindung aus Wasser und/oder Schaum besteht. Niederspannungsanlagen: 1. Schaum: darf grundsätzlich nur in spannungsfreien Anlagen eingesetzt werden; erforderlichenfalls sind auch benachbarte Anlagen spannungsfrei zu machen. Ausgenommen von dieser Beschränkung ist der Einsatz typgeprüfter Löschgeräte und deren Verwendung in elektrischen Anlagen. 2. Druckluftschaum: - keine Gefahr über den Löschmittelstrahl besteht, wenn die Mindestabstände in Zeile 6 eingehalten werden, - anhaftender Schaum an unter Spannung stehenden Teilen führt zu Spannungsverschleppungen, und die Einsatzkräfte können über einen damit in Verbindung stehenden Schaumteppich gefährdet werden (siehe Bild 2). Hochspannungsanlagen: Schaum darf ohne Ausnahmen nur bei spannungsfreien Anlagenteilen eingesetzt werden; erforderlichenfalls sind auch benachbarte Anlagenteile spannungsfrei zu machen, denn es besteht ansonsten die Gefahr der explosionsartigen Zerstörung der elektrischen Anlage (einhergehend mit z. B. herumfliegenden Teilen und Druckwellen) mit zusätzlicher Gefährdung der Einsatzkräfte. |  |  |  |  |  |  |  |  |
- bib.al.original-language: en
- bib.dp.publication-date: 2018-06-29
- ids.document: 7104561
- ids.tracing: hash-69e24773ea33b7e7a138dc2ac3315000e6a41b945ff83711be44a066ec53eca4
- obj.clause-number: Tabelle 6
- obj.element-name: table
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> tr--8e9b9d1a-8157-4b81-a49d-2d500c597b66--l6uA2CPXgAaW

###### tr--hash-c7a2ac284accfd1885c59a6e7412e78f7e42cc7978bef4076f3b3b9ce5e3366d--0Ho6YHGQYA1j: Löschschaum nach DIN EN 1568 (alle Teile), table extract (provision)
Strahlrohre nach DIN 14365-1:1991-02 oder DIN EN 15182 oder andere Strahlrohre mit Austrittsöffnungen ≤ 25 mm Durchmesser (für alle Strahlrohre gilt: ≤ 235 l/min Wasser-Schaummittelgemisch und C-Kupplung)
- bib.al.original-language: en
- bib.dp.publication-date: 2018-06-29
- ids.document: 7104561
- ids.tracing: hash-c7a2ac284accfd1885c59a6e7412e78f7e42cc7978bef4076f3b3b9ce5e3366d
- obj.clause-number: Tabelle 6
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### tr--8e9b9d1a-8157-4b81-a49d-2d500c597b66--l6uA2CPXgAaW: Schaum (provision)
Bild 2 — Gefährdung der Einsatzkraft durch Spannungsverschleppung über Schaumteppich
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Legende
- bib.al.original-language: en
- bib.dp.publication-date: 2018-06-29
- ids.document: 7104561
- ids.tracing: hash-1d612162f99eb0e144b2c19dea0560362e2f6c7eb553ebaa5c3e553bed1b2e50
- obj.clause-number: 6.2.3
- obj.element-name: figure
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### R275: Pulver (heading)
- bib.al.original-language: en
- bib.dp.publication-date: 2018-06-29
- ids.document: 7104561
- obj.clause-number: 6.2.4
- obj.element-name: heading
- obj.language: de
- obj.specobject-type: heading
- ChapterName: 6.2.4 Pulver

##### tr--hash-d1a03f407e82227b0b5a4f6dc5374fa811ebc9e80a547bf4db973ae47dfd6cb8--xLFyCUBtdZIm: Pulver (provision)
Für den Einsatz von Pulver gilt Tabelle 7.
- bib.al.original-language: en
- bib.dp.publication-date: 2018-06-29
- ids.document: 7104561
- ids.tracing: hash-d1a03f407e82227b0b5a4f6dc5374fa811ebc9e80a547bf4db973ae47dfd6cb8
- obj.clause-number: 6.2.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> tr--8e9b9d1a-8157-4b81-a49d-2d500c597b66--CJwqTDnemN2n

##### tr--8e9b9d1a-8157-4b81-a49d-2d500c597b66--CJwqTDnemN2n: Löschpulver nach DIN EN 615 (provision)
Tabelle 7 — Löschpulver nach DIN EN 615
| Lfd.Nr. | Geräte/ Anwendungsform | Wirksame Wurfweite (Mittelwert) m | Eignung für Brandklasse nach DIN EN 2 | Mindestabstände (m) zwischen Löschmittelaustrittsöffnung und unter Spannung stehenden Anlagenteilen |  |  |  |  |
| --- | --- | --- | --- | --- | --- | --- | --- | --- |
| Lfd.Nr. | Geräte/ Anwendungsform | Wirksame Wurfweite (Mittelwert) m | Eignung für Brandklasse nach DIN EN 2 | Niederspannung bis | Hochspannung bis AC |  |  |  |
| Lfd.Nr. | Geräte/ Anwendungsform | Wirksame Wurfweite (Mittelwert) m | Eignung für Brandklasse nach DIN EN 2 | AC 1 000 V oder DC 1 500 V | 30 kV | 110 kV | 220 kV | 380 kV |
| 1 | Tragbare Feuerlöscher nach DIN EN 3 (alle Teile) |  | B, C | 1 | 3^a | 3 | 4 | 5 |
| 1 | Tragbare Feuerlöscher nach DIN EN 3 (alle Teile) | 2 bis 6 | A, B, C | 1 | Einsatz nur in spannungsfreien Anlagenteilen |  |  |  |
| 1 | Tragbare Feuerlöscher nach DIN EN 3 (alle Teile) | 0 bis 1 | D | 1 | Einsatz nur in spannungsfreien Anlagenteilen |  |  |  |
| 2 | Sonstige Geräte, z. B. fahrbare Feuerlöscher | 6 bis 10 | B, C | 1 | 3^a | 3 | 4 | 5 |
| 2 | Sonstige Geräte, z. B. fahrbare Feuerlöscher |  | A, B, C | 1 | Einsatz nur in spannungsfreien Anlagenteilen |  |  |  |
| ^a Bei Aufsicht durch elektrotechnisch unterwiesene Personen oder Elektrofachkräfte ist ein Mindestabstand von 2 m zulässig. |  |  |  |  |  |  |  |  |
| Gefahrenhinweise/Einsatzbeschränkungen Der Einsatz von Löschpulver in elektrischen Anlagen und in deren Nähe darf nur mit Zustimmung des Anlagenbetreibers erfolgen. Beim Einsatz von Löschpulver ist zu beachten: Unter Einfluss von Temperatur, Nässe und Luftfeuchte können Löschpulverbeläge auf Isolatoren in einem Maße leitfähig werden, dass unter Einfluss höherer elektrischer Feldstärken, d. h. im Allgemeinen bei Hochspannung, kurzschlussartige Ströme zum Fließen kommen. Die dadurch entstehenden Störlichtbögen stellen eine Lebensgefahr für sich in der Nähe aufhaltende Personen und eine Gefährdung der Anlage dar. Aus diesem Grunde dürfen Löschpulver in Freiluft- und Innenraumanlagen nur angewendet werden, wenn diese Anlagen trocken sind. Die geforderten Mindestabstände zwischen Löschmittelaustrittsöffnung und unter Spannung stehenden Teilen der elektrischen Anlage dienen der Sicherheit des den Löscheinsatz durchführenden Personals vor direkten Stromeinwirkungen während des Löscheinsatzes. Leitfähige Beläge können in Hochspannungsanlagen Personen und die Anlagen selbst gefährden. Sie sind deshalb nach Möglichkeit zu vermeiden. Es sollten außerdem nur Löschpulver verwendet werden, die keine schwer zu reinigenden Beläge (z. B. Schmelzbeläge bei ABC-Pulver) auf den Anlagenteilen bilden. Der Einsatz von Löschpulver ist im Bereich staubempfindlicher Anlagen (wie Fernmeldeanlagen, Informationsverarbeitungsanlagen, Mess- und Regelanlagen, Verteilerschränken mit Schützen und Relais usw.) zu vermeiden. |  |  |  |  |  |  |  |  |
- bib.al.original-language: en
- bib.dp.publication-date: 2018-06-29
- ids.document: 7104561
- ids.tracing: hash-0d94cc205994251978531d172d7414e8e393f897c7d12bd0ae42f23bc9c671f2
- obj.clause-number: Tabelle 7
- obj.element-name: table
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### R278: Kohlenstoffdioxid (heading)
- bib.al.original-language: en
- bib.dp.publication-date: 2018-06-29
- ids.document: 7104561
- obj.clause-number: 6.2.5
- obj.element-name: heading
- obj.language: de
- obj.specobject-type: heading
- ChapterName: 6.2.5 Kohlenstoffdioxid

##### tr--hash-65ea7381e8918367049c74bd72148944af0dde7226fe3f21975f09978b04fa55--Us1bq9wuUvCf: Kohlenstoffdioxid (provision)
Für den Einsatz von Kohlenstoffdioxid gilt Tabelle 8.
- bib.al.original-language: en
- bib.dp.publication-date: 2018-06-29
- ids.document: 7104561
- ids.tracing: hash-65ea7381e8918367049c74bd72148944af0dde7226fe3f21975f09978b04fa55
- obj.clause-number: 6.2.5
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> tr--8e9b9d1a-8157-4b81-a49d-2d500c597b66--bwNCElvhiiU1

##### tr--8e9b9d1a-8157-4b81-a49d-2d500c597b66--bwNCElvhiiU1: Löschmittel Kohlenstoffdioxid (CO2) (provision)
Tabelle 8 — Löschmittel Kohlenstoffdioxid (CO_2)
| Lfd.Nr. | Geräte/ Anwendungsform | Wirksame Wurfweite (Mittelwert) m | Eignung für Brandklasse nach DIN EN 2 | Mindestabstände (m) zwischen Löschmittelaustrittsöffnung und unter Spannung stehenden Anlagenteilen |  |  |  |  |
| --- | --- | --- | --- | --- | --- | --- | --- | --- |
| Lfd.Nr. | Geräte/ Anwendungsform | Wirksame Wurfweite (Mittelwert) m | Eignung für Brandklasse nach DIN EN 2 | Niederspannung bis | Hochspannung bis AC |  |  |  |
| Lfd.Nr. | Geräte/ Anwendungsform | Wirksame Wurfweite (Mittelwert) m | Eignung für Brandklasse nach DIN EN 2 | AC 1 000 V oder DC 1 500 V | 30 kV | 110 kV | 220 kV | 380 kV |
| 1 | Tragbare Feuerlöscher nach DIN EN 3 (alle Teile) | 2 bis 3 | B | 1 | 3^a | 3 | 4 | 5 |
| 2 | Sonstige Geräte, z. B. fahrbare Feuerlöscher | 3 bis 4 | B |  |  |  |  |  |
| - a Bei Aufsicht durch elektrotechnisch unterwiesene Personen oder Elektrofachkräfte ist ein Mindestabstand von 2 m zulässig. |  |  |  |  |  |  |  |  |
| Gefahrenhinweise/Einsatzbeschränkungen Kohlenstoffdioxid ist elektrisch nichtleitend und hinterlässt keine Rückstände. Die Anwendung ist bei unter Spannung stehenden Anlagen unbedenklich, wenn die Mindestabstände eingehalten werden. Kohlenstoffdioxid ist schwerer als Luft, ist ab 5 % Volumenanteilen gesundheitsgefährdend und wirkt ab 8 % lebensbedrohlich. Vorsicht bei Verwendung in engen, schlecht belüfteten Räumen. Lebensgefahr! Gefahrenhinweise auf den Löschgeräten beachten. In Außenanlagen ist die Wirkung begrenzt, weil sich Kohlenstoffdioxid verflüchtigt. |  |  |  |  |  |  |  |  |
- bib.al.original-language: en
- bib.dp.publication-date: 2018-06-29
- ids.document: 7104561
- ids.tracing: hash-6a792c51abe3c1fa974c046ea7fd5f1f7af941452e632547b236092a311ec692
- obj.clause-number: Tabelle 8
- obj.element-name: table
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

## R281: Maßnahmen nach einem Brand (heading)
- bib.al.original-language: en
- bib.dp.publication-date: 2018-06-29
- ids.document: 7104561
- obj.clause-number: 7
- obj.element-name: heading
- obj.language: de
- obj.specobject-type: heading
- ChapterName: 7 Maßnahmen nach einem Brand

### R282: 7.1 (heading)
- bib.al.original-language: en
- bib.dp.publication-date: 2018-06-29
- ids.document: 7104561
- obj.element-name: heading
- obj.language: de
- obj.specobject-type: heading

#### tr--hash-150d53c8f654bcad6bff3011216f459b67e84a6df8ead5337e2efde8500005fa--NkP9tjSQhj17 (provision)
Beim Betreten der Brandstelle ist besondere Vorsicht erforderlich.
- bib.al.original-language: en
- bib.dp.publication-date: 2018-06-29
- ids.document: 7104561
- ids.tracing: hash-150d53c8f654bcad6bff3011216f459b67e84a6df8ead5337e2efde8500005fa
- obj.clause-number: 7.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### R284: 7.2 (heading)
- bib.al.original-language: en
- bib.dp.publication-date: 2018-06-29
- ids.document: 7104561
- obj.element-name: heading
- obj.language: de
- obj.specobject-type: heading

#### tr--hash-d046c0c9f3c528f0fb43af1e9a5df3b73e58f8c2f3a4ee763a3d68639201c2f7--Rv36fmrzkpga (provision)
Es besteht die Gefahr, dass vorhandene Metallteile unter Spannung stehen können, also nicht nur elektrische Leitungen und Geräte, sondern auch metallene Rohrleitungen, Dachrinnen oder Drahtzäune, sofern sie mit unter Spannung stehenden Anlagenteilen in Berührung stehen.
- bib.al.original-language: en
- bib.dp.publication-date: 2018-06-29
- ids.document: 7104561
- ids.tracing: hash-d046c0c9f3c528f0fb43af1e9a5df3b73e58f8c2f3a4ee763a3d68639201c2f7
- obj.clause-number: 7.2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### R286: 7.3 (heading)
- bib.al.original-language: en
- bib.dp.publication-date: 2018-06-29
- ids.document: 7104561
- obj.element-name: heading
- obj.language: de
- obj.specobject-type: heading

#### tr--hash-e2edbfe8d8ef426d8ea0382730b1b53dfda09e2c5170b867928e7577398d0617--0LBKRqEJ4Gnb (provision)
Nach dem Brand ist der Brandraum zu lüften, bevor Personen ohne Atemschutz den Raum betreten, wobei zu vermeiden ist, dass sich giftige und korrosive Zersetzungsprodukte im Gebäude ausbreiten (siehe 5.1.7).
- bib.al.original-language: en
- bib.dp.publication-date: 2018-06-29
- ids.document: 7104561
- ids.tracing: hash-e2edbfe8d8ef426d8ea0382730b1b53dfda09e2c5170b867928e7577398d0617
- obj.clause-number: 7.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R178

#### tr--hash-9fb932f2453bcd31816521d757e7e7e8538e4556949a884acb07844b73ef5e53--E1A5AnAmVn1R (provision)
Unbefugte Personen dürfen die Brandstelle nicht betreten.
- bib.al.original-language: en
- bib.dp.publication-date: 2018-06-29
- ids.document: 7104561
- ids.tracing: hash-9fb932f2453bcd31816521d757e7e7e8538e4556949a884acb07844b73ef5e53
- obj.clause-number: 7.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### R289: 7.4 (heading)
- bib.al.original-language: en
- bib.dp.publication-date: 2018-06-29
- ids.document: 7104561
- obj.element-name: heading
- obj.language: de
- obj.specobject-type: heading

#### tr--hash-9184e9ded770e6639a5e659970597ea7cac03d9c559fd486328a62565119027d--d3vzshME9UxZ (provision)
Besteht Verdacht, dass Personen mit giftigen Zersetzungsprodukten in Kontakt gekommen sind, müssen sie unverzüglich fachärztlicher Betreuung zugeführt werden.
- bib.al.original-language: en
- bib.dp.publication-date: 2018-06-29
- ids.document: 7104561
- ids.tracing: hash-9184e9ded770e6639a5e659970597ea7cac03d9c559fd486328a62565119027d
- obj.clause-number: 7.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### R291: 7.5 (heading)
- bib.al.original-language: en
- bib.dp.publication-date: 2018-06-29
- ids.document: 7104561
- obj.element-name: heading
- obj.language: de
- obj.specobject-type: heading

#### tr--hash-2d2411853ed796090fe94b1fd6bf604b8a4ccd82bf1fe87f2ccd8f30b2fb879c--qtxpg2KwgM9p (provision)
Unter Spannung stehende elektrische Anlagenteile sind gegen direktes Berühren zu sichern, siehe DIN VDE 0105-100 (VDE 0105-100) .
- bib.al.original-language: en
- bib.dp.publication-date: 2018-06-29
- ids.document: 7104561
- ids.tracing: hash-2d2411853ed796090fe94b1fd6bf604b8a4ccd82bf1fe87f2ccd8f30b2fb879c
- obj.clause-number: 7.5
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### R293: 7.6 (heading)
- bib.al.original-language: en
- bib.dp.publication-date: 2018-06-29
- ids.document: 7104561
- obj.element-name: heading
- obj.language: de
- obj.specobject-type: heading

#### tr--hash-8cd0a9648d7eff9bbce23ad31516bf54159be1b2e193e541ccddb15683ac1e1e--s9uSs0339ZXI (provision)
Pulverbeläge auf Isolatoren können zu Schäden führen und sollten möglichst bald nach Beendigung der Löscharbeiten beseitigt werden.
- bib.al.original-language: en
- bib.dp.publication-date: 2018-06-29
- ids.document: 7104561
- ids.tracing: hash-8cd0a9648d7eff9bbce23ad31516bf54159be1b2e193e541ccddb15683ac1e1e
- obj.clause-number: 7.6
- obj.element-name: paragraph
- obj.language: de
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

### R295: 7.7 (heading)
- bib.al.original-language: en
- bib.dp.publication-date: 2018-06-29
- ids.document: 7104561
- obj.element-name: heading
- obj.language: de
- obj.specobject-type: heading

#### tr--hash-74d58280bc010b041af37a7a75a3094b24e46796a1e3fbcc98eb37952cf6a103--lErLNy4A6hmm (provision)
Die Freigabe oder gegebenenfalls die Wiederinbetriebnahme elektrischer Anlagen darf in Hochspannungsanlagen nur durch den Anlagenverantwortlichen erfolgen.
- bib.al.original-language: en
- bib.dp.publication-date: 2018-06-29
- ids.document: 7104561
- ids.tracing: hash-74d58280bc010b041af37a7a75a3094b24e46796a1e3fbcc98eb37952cf6a103
- obj.clause-number: 7.7
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

## R297: Erste Maßnahmen bei Unfällen durch elektrischen Strom (heading)
- bib.al.original-language: en
- bib.dp.publication-date: 2018-06-29
- ids.document: 7104561
- obj.clause-number: 8
- obj.element-name: heading
- obj.language: de
- obj.specobject-type: heading
- ChapterName: 8 Erste Maßnahmen bei Unfällen durch elektrischen Strom

### tr--hash-8b25997886f1b1ef980335c1bf2e1b5d9e639e0e76865a5bffe3e592ce12ef2f--V8pHEWvpZcF3: Erste Maßnahmen bei Unfällen durch elektrischen Strom (provision)
Für Erste-Hilfe-Maßnahmen siehe DGUV Information 204-006 „Anleitung zur Ersten Hilfe“ und DGUV Fachinformation „Stromunfall - Ärztliche Vorstellung notwendig“.
- bib.al.original-language: en
- bib.dp.publication-date: 2018-06-29
- ids.document: 7104561
- ids.tracing: hash-8b25997886f1b1ef980335c1bf2e1b5d9e639e0e76865a5bffe3e592ce12ef2f
- obj.clause-number: 8
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### R299: 8.1 (heading)
- bib.al.original-language: en
- bib.dp.publication-date: 2018-06-29
- ids.document: 7104561
- obj.element-name: heading
- obj.language: de
- obj.specobject-type: heading

#### tr--hash-e5c656980ca09274671afa107ec5586c15c291ef86afb2b754925eecdbd54051--f7dUNTJUKFnm (provision)
Beim Berühren von unter Spannung stehenden Teilen besteht Lebensgefahr.
- bib.al.original-language: en
- bib.dp.publication-date: 2018-06-29
- ids.document: 7104561
- ids.tracing: hash-e5c656980ca09274671afa107ec5586c15c291ef86afb2b754925eecdbd54051
- obj.clause-number: 8.1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-2306508e407ef641be0a5ac526d5c00bdf3a35c7bb09fdc429de1d96d94da9f7--k1zXVJflKCmr (provision)
Außer Verbrennungen kann der elektrische Strom eine Muskelverkrampfung, die zur Atemlähmung führen kann, und Herzkammerflimmern verursachen.
- bib.al.original-language: en
- bib.dp.publication-date: 2018-06-29
- ids.document: 7104561
- ids.tracing: hash-2306508e407ef641be0a5ac526d5c00bdf3a35c7bb09fdc429de1d96d94da9f7
- obj.clause-number: 8.1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-2ba092debafb70a481a29795b6c1fe9836faada6396cab17220bd824649fca31--mB7WOIbTF33y (provision)
Ein Verunglückter ist so schnell wie möglich von der Spannung zu trennen (siehe 8.2 und 8.3).
- bib.al.original-language: en
- bib.dp.publication-date: 2018-06-29
- ids.document: 7104561
- ids.tracing: hash-2ba092debafb70a481a29795b6c1fe9836faada6396cab17220bd824649fca31
- obj.clause-number: 8.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R303
- cross-reference -> R307

### R303: 8.2 (heading)
- bib.al.original-language: en
- bib.dp.publication-date: 2018-06-29
- ids.document: 7104561
- obj.element-name: heading
- obj.language: de
- obj.specobject-type: heading

#### tr--hash-45592cce02e564e031d4154ab912a306958fab95446fe74de7281d8f06cf61fc--a9uBEAJIDNoo (provision)
In Niederspannungsanlagen ist zunächst die betreffende Leitung spannungsfrei zu machen, da eine vorherige Berührung des Verunglückten den Helfer selbst gefährdet.
- bib.al.original-language: en
- bib.dp.publication-date: 2018-06-29
- ids.document: 7104561
- ids.tracing: hash-45592cce02e564e031d4154ab912a306958fab95446fe74de7281d8f06cf61fc
- obj.clause-number: 8.2
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-8a961e547fcc146e6463283a9e68465d17735169eff32fc55d614402005eb6aa--Ic6FW0BhnKu9 (provision)
Ist dies nicht möglich, dann kann man den Verunglückten von gut isoliertem Standort aus (trockenes Holz, trockene Kleider) von den Leitungen oder Geräten wegziehen.
- bib.al.original-language: en
- bib.dp.publication-date: 2018-06-29
- ids.document: 7104561
- ids.tracing: hash-8a961e547fcc146e6463283a9e68465d17735169eff32fc55d614402005eb6aa
- obj.clause-number: 8.2
- obj.element-name: paragraph
- obj.language: de
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

#### tr--hash-9eb25e846e76d6680771f079e03dee995f2daad0f5cfead1968c7502891c6920--oo2COorsc5td (provision)
Dabei darf man unbedeckte Körperteile nicht mit ungeschützten Händen berühren, sondern muss sich z. B. trockener Decken, Kleider, Handschuhe, Holzlatten bedienen.
- bib.al.original-language: en
- bib.dp.publication-date: 2018-06-29
- ids.document: 7104561
- ids.tracing: hash-9eb25e846e76d6680771f079e03dee995f2daad0f5cfead1968c7502891c6920
- obj.clause-number: 8.2
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### R307: 8.3 (heading)
- bib.al.original-language: en
- bib.dp.publication-date: 2018-06-29
- ids.document: 7104561
- obj.element-name: heading
- obj.language: de
- obj.specobject-type: heading

#### tr--hash-386fe01843a67cb4bd65e7665edc6b96966195f06374c4d054c94fc54201139e--zNYTyP5Lcesd (provision)
Bei Hochspannungsanlagen dürfen nur Elektrofachkräfte und elektrotechnisch unterwiesene Personen eingreifen.
- bib.al.original-language: en
- bib.dp.publication-date: 2018-06-29
- ids.document: 7104561
- ids.tracing: hash-386fe01843a67cb4bd65e7665edc6b96966195f06374c4d054c94fc54201139e
- obj.clause-number: 8.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-d2b13b9e04b4885b51a713dab3f547f2645919148b829cc2d3e7e61f38e9dd87--LUhCkFE4wJNK (provision)
Auch die Annäherung (siehe 5.3.4 und 5.3.5) an den Verunglückten ist gefährlich.
- bib.al.original-language: en
- bib.dp.publication-date: 2018-06-29
- ids.document: 7104561
- ids.tracing: hash-d2b13b9e04b4885b51a713dab3f547f2645919148b829cc2d3e7e61f38e9dd87
- obj.clause-number: 8.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R209
- cross-reference -> R216

### R310: 8.4 (heading)
- bib.al.original-language: en
- bib.dp.publication-date: 2018-06-29
- ids.document: 7104561
- obj.element-name: heading
- obj.language: de
- obj.specobject-type: heading

#### tr--hash-ca72ae5f6606e366fd9bf6fdf7a6abe78d7e9989719e349b6d798178a2c35128--Qw6zD7F4flmh (provision)
Brennende Personen sind am Fortlaufen zu hindern und notfalls am Boden zu wälzen.
- bib.al.original-language: en
- bib.dp.publication-date: 2018-06-29
- ids.document: 7104561
- ids.tracing: hash-ca72ae5f6606e366fd9bf6fdf7a6abe78d7e9989719e349b6d798178a2c35128
- obj.clause-number: 8.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-c2bf9d7cacff8f3e7e7abea902b03d5426f5b54eb7d3744a559456a9d4893eca--K4F6Tk6mANCe (provision)
Zum Ablöschen brennender Kleidung an Personen eignen sich insbesondere Wasser, Feuerlöscher oder Löschdecken.
- bib.al.original-language: en
- bib.dp.publication-date: 2018-06-29
- ids.document: 7104561
- ids.tracing: hash-c2bf9d7cacff8f3e7e7abea902b03d5426f5b54eb7d3744a559456a9d4893eca
- obj.clause-number: 8.4
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-ec2fe9ef9461a394f452e469c2c5aee54f34e72810a2a21de00a6a670f82a8db--QfX91AA9szs7 (provision)
Auch das Einhüllen mit anderen Decken, ausgenommen brennbare Kunststoffdecken, kann helfen.
- bib.al.original-language: en
- bib.dp.publication-date: 2018-06-29
- ids.document: 7104561
- ids.tracing: hash-ec2fe9ef9461a394f452e469c2c5aee54f34e72810a2a21de00a6a670f82a8db
- obj.clause-number: 8.4
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-6cfd6fd99f4b1bba2b9f006389c1b2194aa40eb041b76ae518fb4f91fc38bafd--SxXSwVVWaOjd (provision)
Es können auch andere Löschmittel eingesetzt werden, wenn nur damit schnell gelöscht werden kann, da dies als Rettungsmaßnahme Vorrang vor anderen Überlegungen haben muss.
- bib.al.original-language: en
- bib.dp.publication-date: 2018-06-29
- ids.document: 7104561
- ids.tracing: hash-6cfd6fd99f4b1bba2b9f006389c1b2194aa40eb041b76ae518fb4f91fc38bafd
- obj.clause-number: 8.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### tr--hash-8b08886016a819a4df53eceb43e293ee52bb99e6718b1f2ba9dade2dee9b6593--zNoLIR0mZ2MG (provision)
Wurden andere Löschmittel als Wasser eingesetzt, so ist dies dem erstversorgenden Arzt oder dem Rettungsdienstpersonal mitzuteilen.
- bib.al.original-language: en
- bib.dp.publication-date: 2018-06-29
- ids.document: 7104561
- ids.tracing: hash-8b08886016a819a4df53eceb43e293ee52bb99e6718b1f2ba9dade2dee9b6593
- obj.clause-number: 8.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

## R316: Beurteilung von Gefahren, die von PCB-haltigen Betriebsmitteln ausgehen können (heading)
- bib.al.original-language: en
- bib.dp.publication-date: 2018-06-29
- ids.document: 7104561
- obj.clause-number: Anhang A
- obj.element-name: heading
- obj.language: de
- obj.specobject-type: heading
- ChapterName: Anhang A Beurteilung von Gefahren, die von PCB-haltigen Betriebsmitteln ausgehen können

### tr--hash-16eb697ec0a61056e105ae60f31a69c80168056132f71c340963a65b0fc47a30--q2WYVawJw6MY: Beurteilung von Gefahren, die von PCB-haltigen Betriebsmitteln ausgehen können (provision)
Bei der Beurteilung der Gefahren, die von PCB-haltigen Betriebsmitteln ausgehen können, ist zu unterscheiden:
- Gefährlichkeit der polychlorierten Biphenyle (PCB) bei Brandeinwirkung.
Aus höher chlorierten Biphenylen können sich Spuren giftiger Zersetzungsprodukte bilden (Dibenzodioxin- und Dibenzofuran-Verbindungen).
Maßnahmen: Die Entstehung der Zersetzungsprodukte muss durch raschen und energischen Löschangriff, gegebenenfalls durch Kühlung der PCB-haltigen Betriebsmittel, vermieden werden. Dabei gewähren die Feuerwehreinsatzkleidung, umluftunabhängiger Atemschutz und Kontaminationsschutzhaube ausreichende Sicherheit für die Einsatzkräfte. Besondere Vollschutzanzüge sind unter anderem wegen ihrer geringen thermischen Widerstandsfähigkeit und vor allem wegen der physiologischen Belastung des Personals bei Brandbekämpfung im Innenangriff ungeeignet.
- Gefährlichkeit der polychlorierten Biphenyle (PCB) ohne Brandeinwirkung.
PCB sind nach der Gefahrstoffverordnung als gesundheitsschädlich und umweltgefährdend eingestuft (Andreaskreuz, Xn, N bzw. GHS 08). Wegen ihrer hohen Stabilität sind sie jedoch schwer abbaubar, sie dürfen daher nicht ins Erdreich gelangen.
Maßnahmen: Ausgelaufene Flüssigkeit ist in Behältern aufzufangen oder mit Bindemitteln aufzunehmen und als gefährlicher Abfall zu entsorgen. Es sind Chemikalienschutzhandschuhe zu tragen, gegebenenfalls ist Atemschutz anzulegen; Hautkontakt ist zu vermeiden.
- Waren beim Brand PCB-haltige Betriebsmittel (siehe 4.1.2) beteiligt, ist die Brandstelle zu sperren und zu sichern. Schutzkleidung der Einsatzkräfte und Geräte, die im Einsatz waren, sind an einem Sammelplatz zu lagern. Weitere Maßnahmen sind abhängig von dem Ergebnis der Kontaminationsprüfung.
- bib.al.original-language: en
- bib.dp.publication-date: 2018-06-29
- ids.document: 7104561
- ids.tracing: hash-16eb697ec0a61056e105ae60f31a69c80168056132f71c340963a65b0fc47a30
- obj.clause-number: Anhang A
- obj.element-name: paragraph
- obj.language: de
- obj.modality: requirement
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> R115

## R318: Erläuterungen (heading)
- bib.al.original-language: en
- bib.dp.publication-date: 2018-06-29
- ids.document: 7104561
- obj.clause-number: Anhang B
- obj.element-name: heading
- obj.language: de
- obj.specobject-type: heading
- ChapterName: Anhang B Erläuterungen

### tr--hash-0cddc92b4e2b80679c80af6a0e8036e74e37fd860438295285683609b2655d75--jdMt5Gns8aXz: Erläuterungen (provision)
– Zu Tabelle 1, PV-Anlagen:
- bib.al.original-language: en
- bib.dp.publication-date: 2018-06-29
- ids.document: 7104561
- ids.tracing: hash-0cddc92b4e2b80679c80af6a0e8036e74e37fd860438295285683609b2655d75
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> tr--8e9b9d1a-8157-4b81-a49d-2d500c597b66--4VeEarYSHDTs

### tr--hash-b8523b7e62757090c94075b369d4946358a911a30ffec6a57b25cb53c98c054a--u2SLfuEosEuW: Erläuterungen (provision)
Der Aussage, es tritt durch Mondlicht oder künstliches Licht keine elektrische Gefährdung auf, liegen insbesondere die Untersuchungen von Prof. Häberlin und G. Moine, A. M. Serve zugrunde (siehe Literaturhinweise).
- bib.al.original-language: en
- bib.dp.publication-date: 2018-06-29
- ids.document: 7104561
- ids.tracing: hash-b8523b7e62757090c94075b369d4946358a911a30ffec6a57b25cb53c98c054a
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--hash-a488040b3a9836eb635d8c4d40617dcdce75f7ac2db75f30265ac2ef8e606ae4--vPSg59ciFh5A: Erläuterungen (provision)
Es treten keine lebensbedrohlichen Ströme auf.
- bib.al.original-language: en
- bib.dp.publication-date: 2018-06-29
- ids.document: 7104561
- ids.tracing: hash-a488040b3a9836eb635d8c4d40617dcdce75f7ac2db75f30265ac2ef8e606ae4
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--hash-1e988382441228483d21119b14a233b279d15696470ebb9b1f6349dfe3c34fa7--2YcASaZ4upl7: Erläuterungen (provision)
Eine Körperdurchströmung kann zudem nur auftreten, wenn die Einsatzkraft beide Pole des PV-Generators gleichzeitig berührt.
- bib.al.original-language: en
- bib.dp.publication-date: 2018-06-29
- ids.document: 7104561
- ids.tracing: hash-1e988382441228483d21119b14a233b279d15696470ebb9b1f6349dfe3c34fa7
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--hash-209ef665c56fab3774fb116da5478137bfd7eae40ea1df6a5e7232e1e927e41f--t5ApCp91i4Zp: Erläuterungen (provision)
– Zu Tabelle 5:
- bib.al.original-language: en
- bib.dp.publication-date: 2018-06-29
- ids.document: 7104561
- ids.tracing: hash-209ef665c56fab3774fb116da5478137bfd7eae40ea1df6a5e7232e1e927e41f
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> tr--8e9b9d1a-8157-4b81-a49d-2d500c597b66--QbpMeOdd24Rx

### tr--hash-c144399e8f1f4e558f2f56dc18ba688167f5496cfe0d8dbeb233d3ecee7ef5f3--QbSBXEEfdLgh: Erläuterungen (provision)
Die Vergrößerung der Mindestabstände für Strahlrohre DIN 14365-BM wurde der Einfachheit halber geändert.
- bib.al.original-language: en
- bib.dp.publication-date: 2018-06-29
- ids.document: 7104561
- ids.tracing: hash-c144399e8f1f4e558f2f56dc18ba688167f5496cfe0d8dbeb233d3ecee7ef5f3
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--hash-12b70966a5ac9758407ddfc25ef8c7ef3bd4d6d40314352769b95ada3bf3fe5b--QrFYrnbiZgYW: Erläuterungen (provision)
Der Änderung lagen die Angaben der DIN VDE 0132 (VDE 0132):2001-08 zugrunde, wonach sich der Mindestabstand um 0,75 m für jeden Millimeter, um den sich der Mundstück- bzw. der Düsendurchmesser zwischen 12 mm und 22 mm vergrößert, und in Hochspannungsanlagen um zusätzlich 2 m vergrößert.
- bib.al.original-language: en
- bib.dp.publication-date: 2018-06-29
- ids.document: 7104561
- ids.tracing: hash-12b70966a5ac9758407ddfc25ef8c7ef3bd4d6d40314352769b95ada3bf3fe5b
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--hash-8c38fae10c4a852131b1c2b481884fd4bfefd6490f693596e548ce9ef6f6c0af--0RlejQf9e0m1: Erläuterungen (provision)
Geringere Abstände haben bei Einsätzen, in denen Strahlrohre DIN 14365-BM zur Anwendung kommen, praktisch keine Bedeutung.
- bib.al.original-language: en
- bib.dp.publication-date: 2018-06-29
- ids.document: 7104561
- ids.tracing: hash-8c38fae10c4a852131b1c2b481884fd4bfefd6490f693596e548ce9ef6f6c0af
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--hash-57d8b035bab1db29be420e7c4c26801762cb09449bbbd0f4c6ff15371e41c865--RknkowCROXEl: Erläuterungen (provision)
– Zur Verwendung von Hohlstrahlrohren nach DIN EN 15182-2:
- bib.al.original-language: en
- bib.dp.publication-date: 2018-06-29
- ids.document: 7104561
- ids.tracing: hash-57d8b035bab1db29be420e7c4c26801762cb09449bbbd0f4c6ff15371e41c865
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--hash-c22bf53a30cc59951bfd02cd385ecefc68fe43111cbb3c5f7b27e42e24ccab53--2wjMF3LKjkdd: Erläuterungen (provision)
Mit Druckluftschaum durchgeführte Versuche der vfdb (Vereinigung zur Förderung des deutschen Brandschutzes e. V.) in Kooperation mit DKE/K 213 haben ergeben, dass eine elektrische Gefährdung in Niederspannungsanlagen aufgrund der Zerfallslänge bei Abgabe über Strahlrohre mit einem maximalen Durchfluss von 235 l/min (siehe DIN EN 15182), die mit einer C-Kupplung nach DIN 14307 angeschlossen werden, nicht auftritt.
- bib.al.original-language: en
- bib.dp.publication-date: 2018-06-29
- ids.document: 7104561
- ids.tracing: hash-c22bf53a30cc59951bfd02cd385ecefc68fe43111cbb3c5f7b27e42e24ccab53
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--hash-a9ba6ec822123e392580aae3bcc2c91c6344a071cd6912229849f73c5bc5a567--No976ZUEaLDt: Erläuterungen (provision)
Daher war es auch konsequent, die Tabelle 5 zur Verwendung mit „C“-Hohlstrahlrohren im Rahmen der Anpassung der Tabelle 6 mit anzupassen.
- bib.al.original-language: en
- bib.dp.publication-date: 2018-06-29
- ids.document: 7104561
- ids.tracing: hash-a9ba6ec822123e392580aae3bcc2c91c6344a071cd6912229849f73c5bc5a567
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> tr--8e9b9d1a-8157-4b81-a49d-2d500c597b66--QbpMeOdd24Rx
- cross-reference -> tr--8e9b9d1a-8157-4b81-a49d-2d500c597b66--wIDF0tZG2zG5

### tr--hash-721230f4159c79e73b614c66186b48bf6a8d263eccdf0b6b495c67feba9e4a23--Q1bICJLd7aeo: Erläuterungen (provision)
Gleichwohl wird aufgrund arbeitsschutzrechtlicher Anforderungen empfohlen, anstelle einer einzelfallbezogenen Gefährdungsbeurteilung zur Eignung der Strahlrohre durch den Unternehmer (hier: Feuerwehr) die elektrische Gefährdung im Vorfeld durch die Strahlrohrhersteller zu überprüfen (z. B. durch Messungen analog DIN 14365).
- bib.al.original-language: en
- bib.dp.publication-date: 2018-06-29
- ids.document: 7104561
- ids.tracing: hash-721230f4159c79e73b614c66186b48bf6a8d263eccdf0b6b495c67feba9e4a23
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--hash-bb4374a4700221cb74c8a5a39bcbdfd59a7140f764feb69f037eec263aad64d8--sxqxg1YhR6fS: Erläuterungen (provision)
– Zu Tabelle 6, Zur Verwendung von Schaum in Hochspannungsanlagen:
- bib.al.original-language: en
- bib.dp.publication-date: 2018-06-29
- ids.document: 7104561
- ids.tracing: hash-bb4374a4700221cb74c8a5a39bcbdfd59a7140f764feb69f037eec263aad64d8
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> tr--8e9b9d1a-8157-4b81-a49d-2d500c597b66--wIDF0tZG2zG5

### tr--hash-b04769e456840b18089a54bde77c0408b13cba2cdfe338b8c0d3db0f5cdfe691--XJESNnuX9awS: Erläuterungen (provision)
Durch Schaum werden die Isolationsstrecken beeinträchtigt.
- bib.al.original-language: en
- bib.dp.publication-date: 2018-06-29
- ids.document: 7104561
- ids.tracing: hash-b04769e456840b18089a54bde77c0408b13cba2cdfe338b8c0d3db0f5cdfe691
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### tr--hash-7a271cfd4c87499f5f53469c44f2d01429e9f2d7b6188d87e7e48eba91740798--Hm2dmhIvzzgx: Erläuterungen (provision)
Dies kann zu Erd- und Kurzschlüssen führen, einhergehend mit explosionsartigen Zerstörungen der elektrischen Anlagen.
- bib.al.original-language: en
- bib.dp.publication-date: 2018-06-29
- ids.document: 7104561
- ids.tracing: hash-7a271cfd4c87499f5f53469c44f2d01429e9f2d7b6188d87e7e48eba91740798
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

## R334: Literaturhinweise (heading)
- bib.al.original-language: en
- bib.dp.publication-date: 2018-06-29
- ids.document: 7104561
- obj.element-name: heading
- obj.language: de
- obj.specobject-type: heading

### tr--8e9b9d1a-8157-4b81-a49d-2d500c597b66--vq04x2HO3wXp: Literaturhinweise (provision)
- Verordnung über Sicherheits- und Gesundheitsschutz bei der Bereitstellung von Arbeitsmitteln und deren Benutzung bei der Arbeit, über Sicherheit beim Betrieb überwachungsbedürftiger Anlagen und über die Organisation des betrieblichen Arbeitsschutzes (Betriebssicherheitsverordnung – BetrSichV)
- DGUV Information 204-006 (BGI/GUV-I 503):2011, Information – Anleitung zur Ersten Hilfe
- DGUV Information 203-052 (BGI/GUV-I 8677):2011, Information – Elektrische Gefahren an der Einsatzstelle – Vortrag für Einsatzkräfte
- DGUV Information 200-005 (BGI/GUV-I 8686):2012, Information – Qualifizierung für Arbeiten an Fahrzeugen mit Hochvoltsystemen
- DGUV Vorschrift 1 (BGV A1) (GUV-V A1):2013, Unfallverhütungsvorschrift – Grundsätze der Prävention
- GUV-V C53 (DGUV Vorschrift 49):2005, Unfallverhütungsvorschrift „Feuerwehren“ mit Durchführungsanweisungen
- Verordnung zum Schutz vor Gefahrstoffen (Gefahrstoffverordnung – GefStoffV)
- Häberlin, H., Borgna, L., Schärf, P., PV und Feuerwehr: Keine Panik, realistische Einschätzung der elektrischen Gefahren und möglicher Gegenmaßnahmen, 26. Symposium Photovoltaische Solarenergie Staffelstein, 2011
- Moine, G., Serve, A. M., Campagne de tests Nocturnes sur la Plateforme Photovoltaique Qualiphoton de Transenergie, veröffentlicht durch Direction de la Sécurité Civile (DSC), Syndicat des Energies Renouvables, Transenergie
- bib.al.original-language: en
- bib.dp.publication-date: 2018-06-29
- ids.document: 7104561
- ids.tracing: hash-49b6a6047d7db19b6acee4808eb4eb92419f67b88648849e0ec65f5f546a61c7
- obj.element-name: list-of-documents
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### tr--hash-0cbf94b7c46a2d74ca2d2d62d264270e2c9ed249ac71c5fb1472a18eaa181476--Mz7q8Mkj9H9M: Literaturhinweise, list extract (provision)
- Verordnung über Sicherheits- und Gesundheitsschutz bei der Bereitstellung von Arbeitsmitteln und deren Benutzung bei der Arbeit, über Sicherheit beim Betrieb überwachungsbedürftiger Anlagen und über die Organisation des betrieblichen Arbeitsschutzes (Betriebssicherheitsverordnung – BetrSichV)
- DGUV Information 204-006 (BGI/GUV-I 503):2011, Information – Anleitung zur Ersten Hilfe
- DGUV Information 203-052 (BGI/GUV-I 8677):2011, Information – Elektrische Gefahren an der Einsatzstelle – Vortrag für Einsatzkräfte
- DGUV Information 200-005 (BGI/GUV-I 8686):2012, Information – Qualifizierung für Arbeiten an Fahrzeugen mit Hochvoltsystemen
- DGUV Vorschrift 1 (BGV A1) (GUV-V A1):2013, Unfallverhütungsvorschrift – Grundsätze der Prävention
- GUV-V C53 (DGUV Vorschrift 49):2005, Unfallverhütungsvorschrift „Feuerwehren“ mit Durchführungsanweisungen
- Verordnung zum Schutz vor Gefahrstoffen (Gefahrstoffverordnung – GefStoffV)
- Häberlin, H., Borgna, L., Schärf, P., PV und Feuerwehr: Keine Panik, realistische Einschätzung der elektrischen Gefahren und möglicher Gegenmaßnahmen, 26. Symposium Photovoltaische Solarenergie Staffelstein, 2011
- Moine, G., Serve, A. M., Campagne de tests Nocturnes sur la Plateforme Photovoltaique Qualiphoton de Transenergie, veröffentlicht durch Direction de la Sécurité Civile (DSC), Syndicat des Energies Renouvables, Transenergie
- bib.al.original-language: en
- bib.dp.publication-date: 2018-06-29
- ids.document: 7104561
- ids.tracing: hash-0cbf94b7c46a2d74ca2d2d62d264270e2c9ed249ac71c5fb1472a18eaa181476
- obj.element-name: list-of-documents
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
