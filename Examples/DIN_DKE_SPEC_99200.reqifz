# DIN DKE SPEC 99200:2025-03

# Specification: DIN DKE SPEC 99200:2025-03
- bib.ca.classification: ICS_01.120_Standardization. General rules*ICS_35.240.50_IT applications in industry
- bib.dp.publication-date: 2025-03-01
- bib.tf.title-french: ReqIF™ Interprétation requise pour les normes publiques — Release 1.3 — Texte en anglais
- bib.tg.title-german: ReqIF™-Interpretation für öffentliche Normen — Release 1.3 — Text Englisch
- bib.ti.title-english: ReqIF™ interpretation for public standards — Release 1.3 — Text in English
- bib.ts.document-type: td
- ids.document: 100000012
- pub.software: VDE CaaS 1.5.16
- pub.supplier: VDE
- pub.transformation-date: 2025-07-02T11:49:00.17131435Z

## pkn--100000012: ReqIF™ Interprétation requise pour les normes publiques — Release 1.3 — Texte en anglais (document)
DIN DKE SPEC 99200:2025-03
- bib.al.original-language: en
- bib.ca.classification: ICS_01.120_Standardization. General rules*ICS_35.240.50_IT applications in industry
- bib.dp.publication-date: 2025-03-01
- bib.tg.title-german: ReqIF™-Interpretation für öffentliche Normen — Release 1.3 — Text Englisch
- bib.ti.title-english: ReqIF™ interpretation for public standards — Release 1.3 — Text in English
- bib.ts.document-type: td
- ids.document: 100000012
- obj.language: en
- obj.specobject-type: document
- pub.harmonization: IDiS ReqIF interpretation for public standards 1.3
- pub.originator: DKE
- pub.software: VDE CaaS 1.5.16
- pub.supplier: VDE
- pub.transformation-date: 2025-07-02T11:49:00.17131435Z
- pub.url: https://[changeme].dke.de/api/publications/100000012/reqif

## R2: Contents (heading)
- bib.al.original-language: en
- bib.dp.publication-date: 2025-03-01
- ids.document: 100000012
- obj.element-name: heading
- obj.language: en
- obj.specobject-type: heading

## R3: Foreword (heading)
- bib.al.original-language: en
- bib.dp.publication-date: 2025-03-01
- ids.document: 100000012
- obj.element-name: heading
- obj.language: en
- obj.specobject-type: heading

### prov-100000012-1e53c949e05144d: Foreword (provision)
This DIN DKE SPEC has been developed according to the PAS procedure.
- bib.al.original-language: en
- bib.dp.publication-date: 2025-03-01
- ids.document: 100000012
- ids.tracing: hash-95150B924640D0E8A57C4A044ACC7640942A87CA320F1A2FDFFE63444C9FC21B
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-297629b0fbf24ab: Foreword (provision)
The development of a DIN SPEC according to the PAS procedure is carried out in DIN-SPEC-consortiums and does not require the participation of all stakeholders.
- bib.al.original-language: en
- bib.dp.publication-date: 2025-03-01
- ids.document: 100000012
- ids.tracing: hash-ECD84A859E665C9F70A34DEC77686ADE0E213DE85B8EF6C8E8AC2BE3AB9F1A6B
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-b9d6e95747d0483: Foreword (provision)
This document has been developed and adopted by the initiator(s) and authors named below:
- Schaeffler Technologies AG & Co. KG
- Markus Franke
- Dietmar Lochner
- VDE Verband der Elektrotechnik Elektronik Informationstechnik e. V.
- Dirk Buchholz
- Siemens AG
- Heinz Dresbach
- DIN Solutions GmbH
- Andreas Wernicke
- bib.al.original-language: en
- bib.dp.publication-date: 2025-03-01
- ids.document: 100000012
- ids.tracing: hash-A6989FB4C4C83C3D2FA27D001DDFA7C376C7E0B4FA176C379BF5E47CFFDF1AFB
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-3561ca5ddac74f1: Foreword (provision)
At present, there are no standards covering this topic in the body of German Standards.
- bib.al.original-language: en
- bib.dp.publication-date: 2025-03-01
- ids.document: 100000012
- ids.tracing: hash-32738354B889FDD6D7E2872FBDDA4D095A626CDF62859A3E410494AD9CE01AF5
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-eb4f3a811cd9486: Foreword (provision)
DIN DKE SPECs are not part of the body of German Standards.
- bib.al.original-language: en
- bib.dp.publication-date: 2025-03-01
- ids.document: 100000012
- ids.tracing: hash-185DDA38CB6E6CA0CEE31DDE78AFCFA5F6D0420E0A884684DC4DAC2311E262FA
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-fbecb262d67b427: Foreword (provision)
A draft of this DIN DKE SPEC has not been published.
- bib.al.original-language: en
- bib.dp.publication-date: 2025-03-01
- ids.document: 100000012
- ids.tracing: hash-077F06B2C75C8A05BD5C6EBC4005E983BBA8F8635FCFFFD4494EAEAEEFF49102
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-4778237bebee4b9: Foreword (provision)
Despite great efforts to ensure the accuracy, reliability and precision of technical and non-technical information, the DIN-SPEC-consortium cannot give any explicit or implicit assurance or warranty in respect of the accuracy of the document.
- bib.al.original-language: en
- bib.dp.publication-date: 2025-03-01
- ids.document: 100000012
- ids.tracing: hash-3F7D693C4F7F2AFC92EA09611EF7CE937E3E81265D6B1F58657B932095AD6B95
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-37cb04bb48c0420: Foreword (provision)
Users of this document are hereby made aware that the consortium cannot be held liable for any damage or loss.
- bib.al.original-language: en
- bib.dp.publication-date: 2025-03-01
- ids.document: 100000012
- ids.tracing: hash-B4CA4167D89F0514F0810D7E41CB43FE2CA0CBB2F088FF57FA860497607E510F
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-327aa93bc9dc42a: Foreword (provision)
The application of this DIN DKE SPEC does not release users from the responsibility for their own actions and is applied at their own risk.
- bib.al.original-language: en
- bib.dp.publication-date: 2025-03-01
- ids.document: 100000012
- ids.tracing: hash-867215DA57A98D681C92F50EC865894C47CAB8BBD2388A930D9A00913F6DACC3
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-423af5234aba44b: Foreword (provision)
Attention is drawn to the possibility that some of the elements of this document may be the subject of patent rights.
- bib.al.original-language: en
- bib.dp.publication-date: 2025-03-01
- ids.document: 100000012
- ids.tracing: hash-9F0181906C05FA638FE160318CABD6A58E92809B904B0577E0EAAF145FA45884
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-197bbf342446487: Foreword (provision)
DIN shall not be held responsible for identifying any or all such patent rights.
- bib.al.original-language: en
- bib.dp.publication-date: 2025-03-01
- ids.document: 100000012
- ids.tracing: hash-84815868A40E089302F0BC69919EF6F5DCA5BB26C3683535E3F08234C96F7568
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-e9e5139fa13e463: Foreword (provision)
Provision of this document free of charge as a PDF via the DIN Media Webshop has been financed in advance.
- bib.al.original-language: en
- bib.dp.publication-date: 2025-03-01
- ids.document: 100000012
- ids.tracing: hash-96D28E4C06740D79FCE3E3C6560276D2270E4FC71E368D6DE45ECC44B75F1628
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-adc09c5a6e2645d: Foreword (provision)
For current information on this document, please go to DIN’s website (www.din.de) and search for the document number in question.
- bib.al.original-language: en
- bib.dp.publication-date: 2025-03-01
- ids.document: 100000012
- ids.tracing: hash-232F104E25D55A8448D9EFA0198B7FF546482E7C53BE03AE5640086D47F39BCB
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

## R17: Introduction (heading)
- bib.al.original-language: en
- bib.dp.publication-date: 2025-03-01
- ids.document: 100000012
- obj.element-name: heading
- obj.language: en
- obj.specobject-type: heading

### prov-100000012-f8d2d613511f491: Introduction (provision)
As standardization plays a fundamental role in the context of Industry 4.0, the publishers of technical and legislative regulations should drive forward the digital transformation in the interests of their stakeholders.
- bib.al.original-language: en
- bib.dp.publication-date: 2025-03-01
- ids.document: 100000012
- ids.tracing: hash-A24397AAE06779E08C64244BBC476C16EE174AD8EE05EAF756C05C1F1864DADD
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-50643906c910432: Introduction (provision)
This means that paper has largely become obsolete in standardization, and page-oriented PDF files and single-page documents in natural language should be incrementally developed into machine-processable provisions that can be combined or fragmented as thematically required in the value creation process.
- bib.al.original-language: en
- bib.dp.publication-date: 2025-03-01
- ids.document: 100000012
- ids.tracing: hash-5575808CFB66BDEF78A17B32CA2D842AF7E74769508D30580D571FF4C0F3EACF
- obj.element-name: paragraph
- obj.language: en
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-352522a0021e424: Introduction (provision)
Challenges:
- Standard delivering organizations need to focus on the use of provisions and optimize the knowledge of authors and experts to meet the needs of standards users.
- Stakeholders of standard delivering organizations expect interoperable standards content regardless of the publisher or supplier. More specifically, solutions should not be proprietary for DIN, DKE, VDE, VDI or other CEN, CENELEC, IEC and ISO members, but should be compatible at the interfaces from the customer’s point of view (“from a single source”).
- bib.al.original-language: en
- bib.dp.publication-date: 2025-03-01
- ids.document: 100000012
- ids.tracing: hash-D3B6A234B1DDCA6B860429A890F2A851293DA1E71698531C690B956343CCE094
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-9fd94a715f9e454: Introduction (provision)
To support the digital transformation, the German Institute for Standardization (DIN) ^1 and the German Commission for Electrical Engineering (DKE) ^2 have initiated the national Initiative for Digital Standards (IDiS) in Germany.
- bib.al.original-language: en
- bib.dp.publication-date: 2025-03-01
- ids.document: 100000012
- ids.tracing: hash-3756FCA958082EE5EF5394DB83013B57B2B60DCC92F153A81FC8E67A239B5A69
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-bbcb3251fbbc489: Introduction (provision)
1 de: DIN Deutsches Institut für Normung e. V.
- bib.al.original-language: en
- bib.dp.publication-date: 2025-03-01
- ids.document: 100000012
- ids.tracing: hash-DB3AAC4895C112FC7258917F65CFD9C19F1AA65EA9AEE8EC446712ED042A29A1
- obj.element-name: footnote
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-100000012-4fc09bb50fbc4c6: Introduction (provision)
2 de: DKE Deutsche Kommission Elektrotechnik Elektronik Informationstechnik in DIN und VDE
- bib.al.original-language: en
- bib.dp.publication-date: 2025-03-01
- ids.document: 100000012
- ids.tracing: hash-C774C514A24D34FA4A437E0A1D2C588C782A8B9058DBFC494F500100F19957A8
- obj.element-name: footnote
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-100000012-9c6edbdc856245a: Introduction (provision)
The objectives for IDiS are:
- IDiS promotes the development and gradual establishment of the digital standard, to strengthen the competitiveness of the German economy and the future viability of our society in a digitally transformed world.
- IDiS is the leading independent think tank in Germany for the digital standard and its practical application.
- IDiS offers an exclusive expert community and knowledge platform for all aspects of the digital standard.
- bib.al.original-language: en
- bib.dp.publication-date: 2025-03-01
- ids.document: 100000012
- ids.tracing: hash-A7DB5652A466682B83AB2085771280B4EFD1D261EF9E2D2F5696C7CB780BDB65
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-7a0b6d8b489d47d: Introduction (provision)
This specification is based on the user stories determined by stakeholders of the IDiS project “ReqIF™ interpretation for public standards” (see Annex A) and the generic user stories according to the IDiS Whitepaper 2 [8].
- bib.al.original-language: en
- bib.dp.publication-date: 2025-03-01
- ids.document: 100000012
- ids.tracing: hash-D2C09AF049BBF6ABE518883D934842F71540650EAAFFEBD0B997C48E01857768
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R619
- cross-reference -> prov-100000012-996957e8ccc24fe

## R26: Scope (heading)
- bib.al.original-language: en
- bib.dp.publication-date: 2025-03-01
- ids.document: 100000012
- obj.clause-number: 1
- obj.element-name: heading
- obj.language: en
- obj.specobject-type: heading
- ChapterName: 1 Scope

### prov-100000012-b86f38f7f215491: Scope (provision)
This document specifies the ReqIF™ interpretation for public standards, Release 1.3.
- bib.al.original-language: en
- bib.dp.publication-date: 2025-03-01
- ids.document: 100000012
- ids.tracing: hash-E0BA7091DFAA6BEAB294459F8D000737B879FFFC42E4E9C742331B580658ED13
- obj.clause-number: 1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-e73e56a0e0d243b: Scope (provision)
This document specifies requirements on how to use ReqIF™ data types, attributes, attribute values and the semantical interpretation to achieve a unique interpretation of the same content by different stakeholders.
- bib.al.original-language: en
- bib.dp.publication-date: 2025-03-01
- ids.document: 100000012
- ids.tracing: hash-038E6F2A80F4237E426567E7C42BE839C1376FED9A9324871289C46B0DCE6328
- obj.clause-number: 1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-fe426f67a9ed4e5: Scope (provision)
This document covers the application of the ReqIF™ 1.2 format and specification.
- bib.al.original-language: en
- bib.dp.publication-date: 2025-03-01
- ids.document: 100000012
- ids.tracing: hash-CDD1ED3166BFD66D05CB01CEC1223F6AADD2736138C52BD38E1ED4E8D7AA18C1
- obj.clause-number: 1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-a1d1732a2e5445e: Scope (provision)
This document does not adopt or modify the ReqIF™ format and specification themselves.
- bib.al.original-language: en
- bib.dp.publication-date: 2025-03-01
- ids.document: 100000012
- ids.tracing: hash-803FE63D00DED0348D1B6F8FB6ED53BB1B03878D8D9DB58BA52712A029C57643
- obj.clause-number: 1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

## R31: Normative references (heading)
- bib.al.original-language: en
- bib.dp.publication-date: 2025-03-01
- ids.document: 100000012
- obj.clause-number: 2
- obj.element-name: heading
- obj.language: en
- obj.specobject-type: heading
- ChapterName: 2 Normative references

### prov-100000012-f03ef76af7c9413: Normative references (provision)
The following documents are referred to in the text in such a way that some or all of their content constitutes requirements of this document.
- bib.al.original-language: en
- bib.dp.publication-date: 2025-03-01
- ids.document: 100000012
- ids.tracing: hash-1C225EF90F92381EE215EE66E191FE18C1E39F6B92120217FDC4624968F8ECF7
- obj.clause-number: 2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-36335ddb1c324e0: Normative references (provision)
For dated references, only the edition cited applies.
- bib.al.original-language: en
- bib.dp.publication-date: 2025-03-01
- ids.document: 100000012
- ids.tracing: hash-3AB52340F95A3F39D771FBFA8AD0858893A7E2E16CD9844A0E745D632CA178E3
- obj.clause-number: 2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-5344b011fc814f4: Normative references (provision)
For undated references, the latest edition of the referenced document (including any amendments) applies.
- DIN EN ISO 3166-1, Codes for the representation of names of countries and their subdivisions – Part 1: Country code
- DIN ISO 8601-1, Date and time – Representations for information interchange – Part 1: Basic rules
- DIN ISO 10241-1, Terminological entries in standards – Part 1: General requirements and examples of presentation
- ISO 639, Code for individual languages and language groups
- ISO/IEC 40314, Information technology – Mathematical Markup Language (MathML) Version 3.0; 2nd Edition
- ISO/IEC Directives, Part 2, Principles and rules for the structure and drafting of ISO and IEC documents
- Digital material to the ReqIF™ interpretation for public standards. DIN, DKE: Berlin, Offenbach. Internet: https://www.din-dke-spec-99200.de/
- ICS International Classification for Standards – edition 7. ISO: Genève, 2015
- ReqIF Implementation Guideline referring to OMG ReqIF1.2 – Version 1.10. prostep ivip: Darmstadt, 2024-01-26. Internet: https://www.prostep.org/
- Requirements Interchange Format (ReqIF) – Version 1.2. OMG, 2016-07-01. Internet: https://www.omg.org/spec/ReqIF/1.2/
- MathML Core. W3C Working Draft 27 November 2023. Internet: https://www.w3.org/TR/mathml-core/
- Metadata Field Specification. Metadata Consortium (AFNOR, BSI & DIN): Paris, London, Berlin, 2021-06-04. Internet: https://www.din-dke-spec-99200.de/
- XHTML™ 1.0 The Extensible HyperText Markup Language (Second Edition). W3C Recommendation 26 January 2000 revised 1 August 2002. Internet: https://www.w3.org/TR/xhtml1/
- XHTML™ Modularization 1.1 – Second Edition. W3C Recommendation 29 July 2010 superseded 27 March 2018. Internet: https://www.w3.org/TR/xhtml-modularization/
- bib.al.original-language: en
- bib.dp.publication-date: 2025-03-01
- ids.document: 100000012
- ids.tracing: hash-EF5D4D344B0315844D2F739798EE004F1F9266D5C2E41CD9F9502FF9AD65D9DE
- obj.clause-number: 2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

## R35: Terms and definitions (heading)
- bib.al.original-language: en
- bib.dp.publication-date: 2025-03-01
- ids.document: 100000012
- obj.clause-number: 3
- obj.element-name: heading
- obj.language: en
- obj.specobject-type: heading
- ChapterName: 3 Terms and definitions

### prov-100000012-7cdd65551e9c461: Terms and definitions (provision)
For the purposes of this document, the following terms and definitions apply.
- bib.al.original-language: en
- bib.dp.publication-date: 2025-03-01
- ids.document: 100000012
- ids.tracing: hash-185A910AFC1A64A971DB76B82D95FAAF440CBD54A6BA1AF858ED4EA9C669B08B
- obj.clause-number: 3
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-c364f6cab4f647d: Terms and definitions (provision)
DIN and DKE maintain terminological databases for use in standardization at the following addresses:
- DIN-TERMinologieportal: available at https://www.din.de/go/din-term
- DKE-IEV: available at https://www.dke.de/DKE-IEV
- bib.al.original-language: en
- bib.dp.publication-date: 2025-03-01
- ids.document: 100000012
- ids.tracing: hash-C9FDDA966AB23D625AD568A8287FA83AEA1C8D099D9AA9BC13863BEB19DE90DE
- obj.clause-number: 3
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-f135ef27d1f7472: Terms and definitions (provision)
ISO and IEC maintain terminological databases for use in standardization at the following addresses:
- ISO Online browsing platform: available at https://www.iso.org/obp
- IEC Electropedia: available at https://www.electropedia.org/
- bib.al.original-language: en
- bib.dp.publication-date: 2025-03-01
- ids.document: 100000012
- ids.tracing: hash-1F73CC74A34C3B09A70D7841A108DB7E05B643B66D42C9375CEAF6895C20CC16
- obj.clause-number: 3
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-3c6bbac0ac0349a: publicly available standard (provision)
3.1
publicly available standard
public standard
technical rule published by a recognized standardizing body or government organization
Note 1 to entry: For terminology on bodies and types of standards or regulations see ISO/IEC Guide 2.
Note 2 to entry: Although the title of this specification refers only to public standards explicitly, this specification can be agreed on for any type of publicly available technical rules as well as publicly available legislative regulations.
- bib.al.original-language: en
- bib.dp.publication-date: 2025-03-01
- ids.document: 100000012
- ids.tracing: hash-8F15D1EDE657183453DD49F5693EEEFC5FEECCB20BE55D719F61821F9E7083FC
- obj.clause-number: 3.1
- obj.element-name: concept
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-f713a9758b8743c: publicly available standard (provision)
technical rule published by a recognized standardizing body or government organization
- bib.al.original-language: en
- bib.dp.publication-date: 2025-03-01
- ids.document: 100000012
- ids.tracing: hash-67938EC965BD4653C934C8E752574871F11997341445CB33DA0F661B4A85E3EC
- obj.clause-number: 3.1
- obj.element-name: document
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-15f7812f1f2f406: requirements engineering (provision)
3.2
requirements engineering
RE
systematic process of defining, documenting, and maintaining requirements in the engineering design process
- bib.al.original-language: en
- bib.dp.publication-date: 2025-03-01
- ids.document: 100000012
- ids.tracing: hash-7D416D30EBCF2C324F3BFA44B2D8B4D5CB546593FACF4862F1184242A45CAE6D
- obj.clause-number: 3.2
- obj.element-name: concept
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-32c70f01b395491: requirements engineering (provision)
systematic process of defining, documenting, and maintaining requirements in the engineering design process
- bib.al.original-language: en
- bib.dp.publication-date: 2025-03-01
- ids.document: 100000012
- ids.tracing: hash-235C24E95D0E43D45EE90736681E8F0AF017790AFCB7A99C5FD0689F0D4E25F3
- obj.clause-number: 3.2
- obj.element-name: document
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-1c47d3092f21433: requirements management (provision)
3.3
requirements management
RM
partial discipline of requirements engineering
- bib.al.original-language: en
- bib.dp.publication-date: 2025-03-01
- ids.document: 100000012
- ids.tracing: hash-E87A2E9264B341FEFF185ADD07C4B001B23D2AFE27276DAB379673FABF73664A
- obj.clause-number: 3.3
- obj.element-name: concept
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-a3aa7cd47d764d8: requirements management (provision)
partial discipline of requirements engineering
- bib.al.original-language: en
- bib.dp.publication-date: 2025-03-01
- ids.document: 100000012
- ids.tracing: hash-A5DE3A6472D73EC8D061A02B2121F2BEB44194F7A4D50FA9A402A4871296BA74
- obj.clause-number: 3.3
- obj.element-name: document
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-15e32d2b3846429: requirements management system (provision)
3.4
requirements management system
RMS
content management system which is specialized to manage the content and metadata of requirements
- bib.al.original-language: en
- bib.dp.publication-date: 2025-03-01
- ids.document: 100000012
- ids.tracing: hash-9EA6502037C290B0459BC58A1D049BFD82482D8E1C8334CE721C6F888C9AEF6E
- obj.clause-number: 3.4
- obj.element-name: concept
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-e745775e558c47c: requirements management system (provision)
content management system which is specialized to manage the content and metadata of requirements
- bib.al.original-language: en
- bib.dp.publication-date: 2025-03-01
- ids.document: 100000012
- ids.tracing: hash-24275DEC7851958DD466436C2ABD9402D95B560E382B194FD23CC8FFC74BD1FE
- obj.clause-number: 3.4
- obj.element-name: document
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-5c44ee8a5e244f0: ReqIF™ (provision)
3.5
ReqIF™
Requirements Interchange Format™
file format for the exchange requirements, including its associated metadata, between software tools from different vendors
Note 1 to entry: ReqIF™ is a trademark of the Object Management Group, Inc.
Note 2 to entry: Requirements Interchange Format™ is a trademark of the Object Management Group, Inc.
- bib.al.original-language: en
- bib.dp.publication-date: 2025-03-01
- ids.document: 100000012
- ids.tracing: hash-2215FEB1FC2739AB100D5018A986DE92691CA9D8C03607E0B3EB0225504B3D9D
- obj.clause-number: 3.5
- obj.element-name: concept
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-1917fb7700124f6: ReqIF™ (provision)
file format for the exchange requirements, including its associated metadata, between software tools from different vendors
- bib.al.original-language: en
- bib.dp.publication-date: 2025-03-01
- ids.document: 100000012
- ids.tracing: hash-B92D398837228B83E86146920791721433028912629A1D957000D1CD202ADD37
- obj.clause-number: 3.5
- obj.element-name: document
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-c253cf4d935b4fb: SMART Standards (provision)
3.6
SMART Standards
initiative for the digital transformation of standards content across the entire value creation chain with the objective of making the use of content in the context of Industry 4.0 gradually more efficient through increasing automation based on the utility model
Note 1 to entry: The acronym “SMART” (see IDiS Whitepaper 1) is capitalized and stands for:
- Standards;
- Machine;
- Applicable;
- Readable;
- Transferrable.
- bib.al.original-language: en
- bib.dp.publication-date: 2025-03-01
- ids.document: 100000012
- ids.tracing: hash-77EBD0F224297436957CA516F70025BAD47A60DBD33CC108D52593F13799E330
- obj.clause-number: 3.6
- obj.element-name: concept
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-72113d97e74844c: SMART Standards (provision)
initiative for the digital transformation of standards content across the entire value creation chain with the objective of making the use of content in the context of Industry 4.0 gradually more efficient through increasing automation based on the utility model
- bib.al.original-language: en
- bib.dp.publication-date: 2025-03-01
- ids.document: 100000012
- ids.tracing: hash-786B0F18AF6C8F3A37C601433517683FAB2EE27D44F11E251F14D955510C8ECA
- obj.clause-number: 3.6
- obj.element-name: document
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-608dd1857d16435: value creation chain (provision)
3.7
value creation chain
<SMART Standards> process relevant to the digital transformation of standard content with the value-creating process phases
Note 1 to entry: The value-creating process phases (see IDiS Whitepaper 1) are:
- content creation;
- content management;
- content delivery;
- content usage.
- bib.al.original-language: en
- bib.dp.publication-date: 2025-03-01
- ids.document: 100000012
- ids.tracing: hash-E6F206403826387227FDC3565DCB3C0D2829E0333075ED09EFC3F43A787BB4A6
- obj.clause-number: 3.7
- obj.element-name: concept
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-fc699dc2c8a2470: value creation chain (provision)
<SMART Standards> process relevant to the digital transformation of standard content with the value-creating process phases
- bib.al.original-language: en
- bib.dp.publication-date: 2025-03-01
- ids.document: 100000012
- ids.tracing: hash-ED8B7F902304B8D217B66E69B10235272D82FBA7C9EF315A2C02DC1231A42CBA
- obj.clause-number: 3.7
- obj.element-name: document
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-b1a4cee5ac7449d: utility model (provision)
3.8
utility model
level model
<SMART Standards> milestones for the maturity level of the digital transformation, which is measured by the level achieved across the entire value creation chain
EXAMPLE: According to the utility model (see IDiS Whitepaper 1), requirements management matches level 3 of SMART Standards.
- bib.al.original-language: en
- bib.dp.publication-date: 2025-03-01
- ids.document: 100000012
- ids.tracing: hash-647ACF503F59D29CB7526BB52C635CFF31AC2359F90E1B3C34CFFDA0E80CB883
- obj.clause-number: 3.8
- obj.element-name: concept
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-fb0ad4ef31814c8: utility model (provision)
<SMART Standards> milestones for the maturity level of the digital transformation, which is measured by the level achieved across the entire value creation chain
- bib.al.original-language: en
- bib.dp.publication-date: 2025-03-01
- ids.document: 100000012
- ids.tracing: hash-09ABEBCC57FE64B97BDB2B1BF741CCB659193CA4F3B99512EC0D567BFFE1E83B
- obj.clause-number: 3.8
- obj.element-name: document
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

## R55: Challenges (heading)
- bib.al.original-language: en
- bib.dp.publication-date: 2025-03-01
- ids.document: 100000012
- obj.clause-number: 4
- obj.element-name: heading
- obj.language: en
- obj.specobject-type: heading
- ChapterName: 4 Challenges

### prov-100000012-3c0668607fab4f6: Challenges (provision)
The challenges and potentials for improvement for the “ReqIF™ interpretation for public standards” are:
- ReqIF™ is a generic standard that is interpreted on a customer-specific basis;
- provisions: are determined not interoperable sentence-wise, paragraph-wise, division-wise, or intuitively;
- metadata: amount, naming, data types and values are defined on a not interoperable proprietary basis;
- SMART Standards (3.6): added values have not yet been harmonized;
- compatibility between different target software is limited;
- interoperability between companies is limited.
- bib.al.original-language: en
- bib.dp.publication-date: 2025-03-01
- ids.document: 100000012
- ids.tracing: hash-4617D88675F71035A465604337DDF5A868194768EF71CCBA28119352D1E6EAA6
- obj.clause-number: 4
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-c253cf4d935b4fb

## R57: Objectives (heading)
- bib.al.original-language: en
- bib.dp.publication-date: 2025-03-01
- ids.document: 100000012
- obj.clause-number: 5
- obj.element-name: heading
- obj.language: en
- obj.specobject-type: heading
- ChapterName: 5 Objectives

### prov-100000012-7fda4c99da2545d: Objectives (provision)
The objectives of the “ReqIF™ interpretation for public standards” are:
- harmonize ReqIF™ interpretation for public standards;
- improve interoperability between companies;
- integrate document metadata;
- integrate SMART metadata (3.6);
- cooperate with the committees relevant to ReqIF™ standardization;
- create basis for European and international harmonization.
- bib.al.original-language: en
- bib.dp.publication-date: 2025-03-01
- ids.document: 100000012
- ids.tracing: hash-7E14578C1AEBE1CD507CA77B35B47FB3C603E831AA1D1C89D5F83320E0BEBB19
- obj.clause-number: 5
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-c253cf4d935b4fb

## R59: Target software (heading)
- bib.al.original-language: en
- bib.dp.publication-date: 2025-03-01
- ids.document: 100000012
- obj.clause-number: 6
- obj.element-name: heading
- obj.language: en
- obj.specobject-type: heading
- ChapterName: 6 Target software

### prov-100000012-08271015010f486: Target software (provision)
Since compatibility between different target software is limited, the suppliers may provide ReqIF™ file variants optimized for different target software for the time being.
- bib.al.original-language: en
- bib.dp.publication-date: 2025-03-01
- ids.document: 100000012
- ids.tracing: hash-61F777242B286A594347B001F364F067BF4C212E0925C82BF079A394CA276157
- obj.clause-number: 6
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-f00be289e47747d: Target software (provision)
To achieve best interoperability, all stakeholders should improve on using only the preferred standard variant according to this specification and to the provided digital material (see Clause 11).
- bib.al.original-language: en
- bib.dp.publication-date: 2025-03-01
- ids.document: 100000012
- ids.tracing: hash-5017EDEFCAE9025759DE599C98D1948F187BC97FD7D60270D0E30A9D2D9BB50C
- obj.clause-number: 6
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R604

### prov-100000012-fbdc0810e7c24fd: Target software (provision)
This specification is applicable for any target software which can process the version of ReqIF™ specified in Clause 1.
- bib.al.original-language: en
- bib.dp.publication-date: 2025-03-01
- ids.document: 100000012
- ids.tracing: hash-741AF0C8B85313E61FEEB2B65F35D6BE7A8DE4FD8D40EEF48C885EB9B2F22E06
- obj.clause-number: 6
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R26

### prov-100000012-e2c0b0135a624eb: Target software (provision)
This specification has been implemented and so-far tested with the target software of following vendors:
- IBM DOORS Classic ^3 ;
- Jama Connect + Data Exchange^3;
- PTC Codebeamer^3;
- PTC Windchill RV&S + Requirements Connector^3;
- Siemens Polarion^3.
- bib.al.original-language: en
- bib.dp.publication-date: 2025-03-01
- ids.document: 100000012
- ids.tracing: hash-A6C3D932CFB468D75DD1063EF1447146D1650C1F972DA170A490F0A99DC8D970
- obj.clause-number: 6
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-91c9b88ceb1c476: Target software (provision)
3 This is the trade name of a product supplied by the vendor mentioned initially. This information is given for the convenience of users of this document and does not constitute an endorsement by DIN or DKE of the product named. Equivalent products may be used if they can be shown to lead to the same results.
- bib.al.original-language: en
- bib.dp.publication-date: 2025-03-01
- ids.document: 100000012
- ids.tracing: hash-41E3509ADE73C5DC1D2822474BBEE4C6C5B5D3DE21E3D7968736FAC1A2D24A4C
- obj.clause-number: 6
- obj.element-name: footnote
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-100000012-8cc81626ff94475: Target software (provision)
This specification is not limited to the target software of any vendors.
- bib.al.original-language: en
- bib.dp.publication-date: 2025-03-01
- ids.document: 100000012
- ids.tracing: hash-8A8EAD46F1D517D2EDD452D225AA5459AD17D33AB9E0BB995B377F95A6FCDF2D
- obj.clause-number: 6
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

## R66: Application best-practice (heading)
- bib.al.original-language: en
- bib.dp.publication-date: 2025-03-01
- ids.document: 100000012
- obj.clause-number: 7
- obj.element-name: heading
- obj.language: en
- obj.specobject-type: heading
- ChapterName: 7 Application best-practice

### R67: Internal standard versus interchange format (heading)
- bib.al.original-language: en
- bib.dp.publication-date: 2025-03-01
- ids.document: 100000012
- obj.clause-number: 7.1
- obj.element-name: heading
- obj.language: en
- obj.specobject-type: heading
- ChapterName: 7.1 Internal standard versus interchange format

#### prov-100000012-a667d75d2f5f496: Internal standard versus interchange format (provision)
Users have the following options to deal with this specification, depending on the preconditions:
- If the users’ company has no internal standard interpretation for their RMS and this specification matches the user’s requirements, the users should adopt and implement this specification as internal standard to achieve the optimal efficiency and interoperability with other companies.
- If the users’ company has already an internal standard interpretation for their RMS or this specification does not match the user’s requirements, the users should implement this specification for the import and export processes to achieve a sufficient level of interoperability with other companies.
- bib.al.original-language: en
- bib.dp.publication-date: 2025-03-01
- ids.document: 100000012
- ids.tracing: hash-9FD882D1F7692D8B4EAB33A907E4ECA5530E3B7590F6FF8681B1634310A0CAE6
- obj.clause-number: 7.1
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-5e42118628d541c: Internal standard versus interchange format, Note (provision)
NOTE:
Figure 1 illustrates that situation where communication under n stakeholders implies that each stakeholder maintains n − 1 individual import mapping variants, whereas Figure 2 illustrates a situation where communication under n stakeholders via an exchange standard can be achieved with only one import mapping if this specification has been agreed on.
- bib.al.original-language: en
- bib.dp.publication-date: 2025-03-01
- ids.document: 100000012
- ids.tracing: hash-E20EE61F8016C47CF603F912088E11D5F47E66D3560AC7BCF3C20FCB004A73CD
- obj.clause-number: 7.1
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-100000012-9eea83462d234b1
- cross-reference -> prov-100000012-b943da87861e457

#### prov-100000012-9eea83462d234b1: Internal standard versus interchange format (provision)
Figure 1 — n to n communication
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- bib.al.original-language: en
- bib.dp.publication-date: 2025-03-01
- ids.document: 100000012
- ids.tracing: hash-1EBF96E461DCD8E67BE0DF9859CCE618DC7271C5E0DC07187BEB8CBFF356A28D
- obj.clause-number: 7.1
- obj.element-name: figure
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-b943da87861e457: Internal standard versus interchange format (provision)
Figure 2 — n via 1 communication
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- bib.al.original-language: en
- bib.dp.publication-date: 2025-03-01
- ids.document: 100000012
- ids.tracing: hash-075B71BCF832850CCB373DA88DE571EFB69D83DE505624CD313505078B232B02
- obj.clause-number: 7.1
- obj.element-name: figure
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### R72: Configuration issues for target software (heading)
- bib.al.original-language: en
- bib.dp.publication-date: 2025-03-01
- ids.document: 100000012
- obj.clause-number: 7.2
- obj.element-name: heading
- obj.language: en
- obj.specobject-type: heading
- ChapterName: 7.2 Configuration issues for target software

#### prov-100000012-ead7f3457c9c429: Configuration issues for target software (provision)
If ReqIF™ files according to this specification are imported, a common behavior of target software is to sort the attributes in alphabetical instead of the logical order according to the data model (see 8.2).
- bib.al.original-language: en
- bib.dp.publication-date: 2025-03-01
- ids.document: 100000012
- ids.tracing: hash-C5145BB7EDC66E3891F8A418B4690D6E3353D0586E77D9C4FF81D87E35068247
- obj.clause-number: 7.2
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R119

#### prov-100000012-d6196baef39b467: Configuration issues for target software (provision)
If the logical order according to the data model (see 8.2) is preferred, the order of attributes shall be configured for the target software.
- bib.al.original-language: en
- bib.dp.publication-date: 2025-03-01
- ids.document: 100000012
- ids.tracing: hash-59441756A1BC098E49318129FBCE9A81F2D17CFD7989A86A9F85146DACF60533
- obj.clause-number: 7.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R119

#### prov-100000012-6cc4e0d39fd9427: Configuration issues for target software (provision)
If the logical order according to the data model (see 8.2) is preferred, the users should investigate for their target software whether:
- digital material (see 7.3) for the import and configuration is available, i. e. scripts or import templates; or
- support for the configuration can be obtained if demanded.
- bib.al.original-language: en
- bib.dp.publication-date: 2025-03-01
- ids.document: 100000012
- ids.tracing: hash-9E602F3D2DCED391A22EFBD8D079CC1B1A0614A0983C563FF55E0BACA82185E0
- obj.clause-number: 7.2
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R119
- cross-reference -> R76

### R76: Digital material for the import and export process (heading)
- bib.al.original-language: en
- bib.dp.publication-date: 2025-03-01
- ids.document: 100000012
- obj.clause-number: 7.3
- obj.element-name: heading
- obj.language: en
- obj.specobject-type: heading
- ChapterName: 7.3 Digital material for the import and export process

#### prov-100000012-7cccafce59a6432: Digital material for the import and export process (provision)
Digital material to the ReqIF™ interpretation for public standards is provided on the official web page to support the import process, management process and export process in the target software (see Clause 11):
- benchmarking documents for interoperability tests;
- example documents to support understanding and implementing this specification;
- tables to the data model as MS® Excel® ^3 file;
- utilities for the import and export processes (templates);
- Schematron for the validation against the data model of this specification to improve interoperability.
- bib.al.original-language: en
- bib.dp.publication-date: 2025-03-01
- ids.document: 100000012
- ids.tracing: hash-BD63EB1F1BF87924CFA841F976940386FEF52E3CD1FAAD074C4E086B2E957408
- obj.clause-number: 7.3
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R604

#### prov-100000012-96640ed1a02741e: Digital material for the import and export process (provision)
The users should investigate whether digital material is available for their target software.
- bib.al.original-language: en
- bib.dp.publication-date: 2025-03-01
- ids.document: 100000012
- ids.tracing: hash-50C821CF21E93162B717BCD83B9A9E1C7D6EEBB14ABF95A25E71AC5B120A6701
- obj.clause-number: 7.3
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-eccbc9e390e944e: Digital material for the import and export process (provision)
Since the digital material is subject of the continuous improvement process, the users should frequently check whether updates of digital material relevant for them is available.
- bib.al.original-language: en
- bib.dp.publication-date: 2025-03-01
- ids.document: 100000012
- ids.tracing: hash-74984797B4056B2C2F3035BBC738E765ED154C3AED54C6B3E31CCE39342F29CB
- obj.clause-number: 7.3
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

### R80: Conforming application (heading)
- bib.al.original-language: en
- bib.dp.publication-date: 2025-03-01
- ids.document: 100000012
- obj.clause-number: 7.4
- obj.element-name: heading
- obj.language: en
- obj.specobject-type: heading
- ChapterName: 7.4 Conforming application

#### prov-100000012-a22f9994159f455: Conforming application (provision)
Requirements for a conforming application of this specification are:
- The data model for this interpretation shall be implemented as specified in Clause 8.
- The attributes shall be implemented as specified in 8.2.
- The attributes for the document shall be implemented as specified in 8.1.2.
- The list of values for attributes shall be implemented as specified in 8.3.
- The declarations and definitions shall be implemented as specified in 8.4, based on the conventions in 8.5.
- The semantic interpretation shall be according to Clause 9.
- The presentation shall be according to Clause 10.
- The ReqIF™ file shall conform to the OMG ReqIF™ 1.2 specification.
- The ReqIF™ file shall validate against the ReqIF™ 1.2 XML Schema Definition.
- The ReqIF™ file shall conform to the actual prostep ReqIF™ 1.2 guideline.
- The ReqIF™ file shall validate against the Schematron for this specification without errors (see 11.5).
- After performing a round-trip process, the DIN DKE benchmarking file shall be without change or loss of attributes, values and without issues relevant for the interpretation of provisions (see 11.1).
- bib.al.original-language: en
- bib.dp.publication-date: 2025-03-01
- ids.document: 100000012
- ids.tracing: hash-798ECE0588D86369EB30904CE1132CAD8506884BC985C41FD2AB0D2C49789347
- obj.clause-number: 7.4
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R82
- cross-reference -> R119
- cross-reference -> R115
- cross-reference -> R140
- cross-reference -> R177
- cross-reference -> R202
- cross-reference -> R205
- cross-reference -> R543
- cross-reference -> R615
- cross-reference -> R605

## R82: Data model (heading)
- bib.al.original-language: en
- bib.dp.publication-date: 2025-03-01
- ids.document: 100000012
- obj.clause-number: 8
- obj.element-name: heading
- obj.language: en
- obj.specobject-type: heading
- ChapterName: 8 Data model

### R83: Structural overview (heading)
- bib.al.original-language: en
- bib.dp.publication-date: 2025-03-01
- ids.document: 100000012
- obj.clause-number: 8.1
- obj.element-name: heading
- obj.language: en
- obj.specobject-type: heading
- ChapterName: 8.1 Structural overview

#### R84: Information on the provision (SpecObject) (heading)
- bib.al.original-language: en
- bib.dp.publication-date: 2025-03-01
- ids.document: 100000012
- obj.clause-number: 8.1.1
- obj.element-name: heading
- obj.language: en
- obj.specobject-type: heading
- ChapterName: 8.1.1 Information on the provision (SpecObject)

##### R85: Content attributes on the provision (SpecObject) (heading)
- bib.al.original-language: en
- bib.dp.publication-date: 2025-03-01
- ids.document: 100000012
- obj.clause-number: 8.1.1.1
- obj.element-name: heading
- obj.language: en
- obj.specobject-type: heading
- ChapterName: 8.1.1.1 Content attributes on the provision (SpecObject)

###### prov-100000012-37fa5549cda748b: Content attributes on the provision (SpecObject) (provision)
The content attributes (see 8.2.1.1) contain the text content of the provision from the public standard.
- bib.al.original-language: en
- bib.dp.publication-date: 2025-03-01
- ids.document: 100000012
- ids.tracing: hash-735C75E897F5D1522B82524B9E4A641320D040D9C84AD424A6AB1C7BE05048C0
- obj.clause-number: 8.1.1.1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R121

###### prov-100000012-5236f64c84434fe: Content attributes on the provision (SpecObject) (provision)
The content attributes shall be provided by the supplier of the ReqIF™ file for the public standard (see 9.6).
- bib.al.original-language: en
- bib.dp.publication-date: 2025-03-01
- ids.document: 100000012
- ids.tracing: hash-94CEDE6617664B7BE5910806DD2DCE5A75B6560D6AB77425264E7DF9D2BF4A29
- obj.clause-number: 8.1.1.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R386

###### prov-100000012-bc2b4d4d42ad4e7: Content attributes on the provision (SpecObject) (provision)
The users can use the content attributes to filter, search and manage provisions.
- bib.al.original-language: en
- bib.dp.publication-date: 2025-03-01
- ids.document: 100000012
- ids.tracing: hash-441C1DF858AC299CC643D2C14D18D9F9FB04ABBFE3A35FD297C4B46268CF446D
- obj.clause-number: 8.1.1.1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-100000012-fd3fcd3fe991417: Content attributes on the provision (SpecObject) (provision)
The content attributes are the first block of the data model to facilitate the most frequent accesses.
- bib.al.original-language: en
- bib.dp.publication-date: 2025-03-01
- ids.document: 100000012
- ids.tracing: hash-B306C57D79B36C3D0EEFC88BAC6556FC74E5BC0E626D0E7061B906B3A96681A3
- obj.clause-number: 8.1.1.1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-100000012-a70758aed4d3473: Content attributes on the provision (SpecObject), Note (provision)
NOTE:
Figure 3 illustrates the information blocks of the data model (see 8.2).
- bib.al.original-language: en
- bib.dp.publication-date: 2025-03-01
- ids.document: 100000012
- ids.tracing: hash-A0AB474A508C27BF4D4ADAD7F4371F08789D5F2091ACC248749A64B444B1C693
- obj.clause-number: 8.1.1.1
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-100000012-dec6308b1e85405
- cross-reference -> R119

###### prov-100000012-dec6308b1e85405: Content attributes on the provision (SpecObject) (provision)
Figure 3 — Data model to the ReqIF™ interpretation for public standards
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- bib.al.original-language: en
- bib.dp.publication-date: 2025-03-01
- ids.document: 100000012
- ids.tracing: hash-60B961D73086C335D9B1A124DEF0953413EDCDEF9E4AFE742BEF8BB2416D9036
- obj.clause-number: 8.1.1.1
- obj.element-name: figure
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### R92: Object attributes on the provision (SpecObject) (heading)
- bib.al.original-language: en
- bib.dp.publication-date: 2025-03-01
- ids.document: 100000012
- obj.clause-number: 8.1.1.2
- obj.element-name: heading
- obj.language: en
- obj.specobject-type: heading
- ChapterName: 8.1.1.2 Object attributes on the provision (SpecObject)

###### prov-100000012-3ef1609304504b7: Object attributes on the provision (SpecObject) (provision)
The object attributes (see 8.2.1.2) contain the description for the characteristics of the provision content, such as the number and heading of its context, its language, and its modality.
- bib.al.original-language: en
- bib.dp.publication-date: 2025-03-01
- ids.document: 100000012
- ids.tracing: hash-5FEBE856803E25E0FD0F5A2A83DB636AA3DEB29C706273198F43DC0C0EAE8172
- obj.clause-number: 8.1.1.2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124

###### prov-100000012-b4c5f6882b674e2: Object attributes on the provision (SpecObject) (provision)
The object attributes should be provided by the supplier of the ReqIF™ file for a public standard (see 9.7).
- bib.al.original-language: en
- bib.dp.publication-date: 2025-03-01
- ids.document: 100000012
- ids.tracing: hash-0706B706862BE20AF2F9B94041049035BC13B2F9078475DD7086408AB3846CC6
- obj.clause-number: 8.1.1.2
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R399

###### prov-100000012-b9576735011c4d1: Object attributes on the provision (SpecObject) (provision)
The users can use the object attributes to filter, search and manage provisions.
- bib.al.original-language: en
- bib.dp.publication-date: 2025-03-01
- ids.document: 100000012
- ids.tracing: hash-C0341D2ADE4706A6E4FB61690359FAB1A7FE735F561DFF9E8CDCEAEE5E3800D9
- obj.clause-number: 8.1.1.2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-100000012-c659f4a2ae754e0: Object attributes on the provision (SpecObject) (provision)
The object attributes are the second block of the data model to facilitate the second-most frequent accesses.
- bib.al.original-language: en
- bib.dp.publication-date: 2025-03-01
- ids.document: 100000012
- ids.tracing: hash-04AC5B2F54C0C51F0E6B7AE6AC161370BF9F33199BC049D420F95AFC487F5763
- obj.clause-number: 8.1.1.2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-100000012-b3a6cf58164a4ed: Object attributes on the provision (SpecObject), Note (provision)
NOTE:
The object attributes are based on the “SMART standard model” (see 3.6).
- bib.al.original-language: en
- bib.dp.publication-date: 2025-03-01
- ids.document: 100000012
- ids.tracing: hash-ADBE023D93ABB7FAD86C10D5D42ED12A1F79CC2D4EF1EB2FEFC60B9ADF242794
- obj.clause-number: 8.1.1.2
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-100000012-c253cf4d935b4fb

##### R98: Use attributes for intra-company management of the provision (SpecObject) (heading)
- bib.al.original-language: en
- bib.dp.publication-date: 2025-03-01
- ids.document: 100000012
- obj.clause-number: 8.1.1.3
- obj.element-name: heading
- obj.language: en
- obj.specobject-type: heading
- ChapterName: 8.1.1.3 Use attributes for intra-company management of the provision (SpecObject)

###### prov-100000012-d5d77c3d4f71403: Use attributes for intra-company management of the provision (SpecObject) (provision)
The use attributes (see 8.2.1.3) are an additional set of standardized metadata to classify provisions, e. g., within the business process, product life cycle or project phase.
- bib.al.original-language: en
- bib.dp.publication-date: 2025-03-01
- ids.document: 100000012
- ids.tracing: hash-76233054439C29F8FEC34DF63353BDCA5EEF2064DE1CC75CDDD588DF8FC2AFA7
- obj.clause-number: 8.1.1.3
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R127

###### prov-100000012-bdad3c38c00147d: Use attributes for intra-company management of the provision (SpecObject) (provision)
Since use attributes can be assigned by end-users only, the use attributes cannot be provided by the supplier of the ReqIF™ file for a public standard (see 9.8).
- bib.al.original-language: en
- bib.dp.publication-date: 2025-03-01
- ids.document: 100000012
- ids.tracing: hash-DB165B5E44C4D22512884EF2C7B6B4F85AC037B562E1657219165CF89443E2D6
- obj.clause-number: 8.1.1.3
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R443

###### prov-100000012-454760f84c47428: Use attributes for intra-company management of the provision (SpecObject) (provision)
The users can use the use attributes to filter, search and manage provisions.
- bib.al.original-language: en
- bib.dp.publication-date: 2025-03-01
- ids.document: 100000012
- ids.tracing: hash-0513D78733FCB41BC1926DB50828FCCC342B89934D0F7F712BE8908273CDF59A
- obj.clause-number: 8.1.1.3
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-100000012-88b9e2e8909745b: Use attributes for intra-company management of the provision (SpecObject) (provision)
The use attributes are the third block of the data model to facilitate the third-most frequent accesses.
- bib.al.original-language: en
- bib.dp.publication-date: 2025-03-01
- ids.document: 100000012
- ids.tracing: hash-CC547023681C44DEAA8CFBEF6FC927170B783F8B7E68450F347C63CD4C03CF56
- obj.clause-number: 8.1.1.3
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-100000012-ffd4d23e67844bf: Use attributes for intra-company management of the provision (SpecObject), Note (provision)
NOTE:
The use attributes are based on the “SMART use model” (see 3.6).
- bib.al.original-language: en
- bib.dp.publication-date: 2025-03-01
- ids.document: 100000012
- ids.tracing: hash-0F50082591496D6CBA45B40C9FBE1893B2CE81E85104CB5A32FBCBAC55E5E15A
- obj.clause-number: 8.1.1.3
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-100000012-c253cf4d935b4fb

##### R104: Bibliographic document metadata (Perinorm 1.000) (heading)
- bib.al.original-language: en
- bib.dp.publication-date: 2025-03-01
- ids.document: 100000012
- obj.clause-number: 8.1.1.4
- obj.element-name: heading
- obj.language: en
- obj.specobject-type: heading
- ChapterName: 8.1.1.4 Bibliographic document metadata (Perinorm 1.000)

###### prov-100000012-1376af6e0b1b44c: Bibliographic document metadata (Perinorm 1.000) (provision)
The bibliographic document metadata (see 8.2.1.4) contain a selection of fields from the set of metadata according to the Metadata Field Specification standardized by the Metadata Consortium of AFNOR, BSI and DIN.
- bib.al.original-language: en
- bib.dp.publication-date: 2025-03-01
- ids.document: 100000012
- ids.tracing: hash-72F644BB95730AE8E14CED8B676FFB7009964AA4B663AA7E1416369900F71B67
- obj.clause-number: 8.1.1.4
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R130

###### prov-100000012-2fece01ea522415: Bibliographic document metadata (Perinorm 1.000) (provision)
The bibliographic document metadata shall be provided by the supplier of the ReqIF™ file for a public standard (see 9.9).
- bib.al.original-language: en
- bib.dp.publication-date: 2025-03-01
- ids.document: 100000012
- ids.tracing: hash-BE659C2AFEEAD2BBA622EA032A4B380DC2145071371607BA2CE10C5456FF08F3
- obj.clause-number: 8.1.1.4
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R488

###### prov-100000012-3285ba613906457: Bibliographic document metadata (Perinorm 1.000) (provision)
The bibliographic document metadata are the fourth block of the data model since accesses to the meta data of the original document are assumed to be less frequent.
- bib.al.original-language: en
- bib.dp.publication-date: 2025-03-01
- ids.document: 100000012
- ids.tracing: hash-99B3CFA66F5D46EB478854D6355B1337DCA5A885E1F77B7079D2A00324086A45
- obj.clause-number: 8.1.1.4
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-100000012-34d80a5d9b74425: Bibliographic document metadata (Perinorm 1.000) (provision)
The users can use the bibliographic document metadata to filter, search and manage provisions.
- bib.al.original-language: en
- bib.dp.publication-date: 2025-03-01
- ids.document: 100000012
- ids.tracing: hash-11D61B96305DE2375E68FE625768BE363311ED874798CDF03BB6A38D87335D01
- obj.clause-number: 8.1.1.4
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-100000012-7c69acf9d0ee4ea: Bibliographic document metadata (Perinorm 1.000), Note (provision)
NOTE:
The Metadata Field Specification of the Metadata Consortium supersedes the Perinorm Field Specification, published as: Perinorm Field Specification. Perinorm Consortium (AFNOR, BSI, DIN), 2009-11.
- bib.al.original-language: en
- bib.dp.publication-date: 2025-03-01
- ids.document: 100000012
- ids.tracing: hash-E7243F8FD6F38F6EC8D8776B151DB736C42D8A7400BF68E1B3D54B457C459367
- obj.clause-number: 8.1.1.4
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### R110: Identification (ID) attributes on the provision (SpecObject) (heading)
- bib.al.original-language: en
- bib.dp.publication-date: 2025-03-01
- ids.document: 100000012
- obj.clause-number: 8.1.1.5
- obj.element-name: heading
- obj.language: en
- obj.specobject-type: heading
- ChapterName: 8.1.1.5 Identification (ID) attributes on the provision (SpecObject)

###### prov-100000012-c74be6e2186343f: Identification (ID) attributes on the provision (SpecObject) (provision)
The identification (ID) attributes (see 8.2.1.5) contain IDs for different user stories (see Clause B.1).
- bib.al.original-language: en
- bib.dp.publication-date: 2025-03-01
- ids.document: 100000012
- ids.tracing: hash-95EDB8006857A32D9B8231E484D24572824AB45415440D35226065C48AC003E5
- obj.clause-number: 8.1.1.5
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R134
- cross-reference -> R629

###### prov-100000012-0218c78f73e245c: Identification (ID) attributes on the provision (SpecObject) (provision)
The identification (ID) attributes shall be provided by the supplier of the ReqIF™ file for a public standard (see 9.10).
- bib.al.original-language: en
- bib.dp.publication-date: 2025-03-01
- ids.document: 100000012
- ids.tracing: hash-E9FA9A9FE36FDD201B1804DAFC7A59C7A41E5180DED8169035BA43FA94A096BF
- obj.clause-number: 8.1.1.5
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R491

###### prov-100000012-efb84e3693db4cb: Identification (ID) attributes on the provision (SpecObject) (provision)
The users can use the identification (ID) attributes to identify provisions, refer to provisions, manage and trace the change history of provisions.
- bib.al.original-language: en
- bib.dp.publication-date: 2025-03-01
- ids.document: 100000012
- ids.tracing: hash-ADBCDF831B0FBD87B76F63448DEE99D586B2F43B5F1E950D6B56ED8FCF608398
- obj.clause-number: 8.1.1.5
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-100000012-33b4d85a3896434: Identification (ID) attributes on the provision (SpecObject) (provision)
The identification (ID) attributes are the fifth block of the data model since accesses to identifiers of the original document are assumed to be less frequent.
- bib.al.original-language: en
- bib.dp.publication-date: 2025-03-01
- ids.document: 100000012
- ids.tracing: hash-3E055B25B0CEF47CCB1C739A57F4B59F53329C32E106A912939FE47B7FE2C1B5
- obj.clause-number: 8.1.1.5
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### R115: Attributes on the document SpecObject for asset or service metadata of the creator, supplier, or publisher (heading)
- bib.al.original-language: en
- bib.dp.publication-date: 2025-03-01
- ids.document: 100000012
- obj.clause-number: 8.1.2
- obj.element-name: heading
- obj.language: en
- obj.specobject-type: heading
- ChapterName: 8.1.2 Attributes on the document SpecObject for asset or service metadata of the creator, supplier, or publisher

##### prov-100000012-496f7da443ee4b7: Attributes on the document SpecObject for asset or service metadata of the creator, supplier, or publisher (provision)
The asset or service metadata (see 8.2.2) contain information from the creator, supplier, or publisher of the ReqIF™ file, such as name of the originator, release of this specification, name and version of the creating software.
- bib.al.original-language: en
- bib.dp.publication-date: 2025-03-01
- ids.document: 100000012
- ids.tracing: hash-EB17AB93031B4E89A07F8E787696ABE7191CD7D9D2F0ED8F43A0551473A52B91
- obj.clause-number: 8.1.2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R137

##### prov-100000012-0e07dd03d514407: Attributes on the document SpecObject for asset or service metadata of the creator, supplier, or publisher (provision)
The bibliographic document metadata should be provided by the supplier of the ReqIF™ file for a public standard (see 9.11).
- bib.al.original-language: en
- bib.dp.publication-date: 2025-03-01
- ids.document: 100000012
- ids.tracing: hash-04D7BC23ED7C665EF70E79093FA658E6ECD4CA5BFFAAD2933A9332B96FDDC8C9
- obj.clause-number: 8.1.2
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R526

##### prov-100000012-b26f819c3d1945d: Attributes on the document SpecObject for asset or service metadata of the creator, supplier, or publisher (provision)
The users can use the asset or service metadata to manage their processes and support issues.
- bib.al.original-language: en
- bib.dp.publication-date: 2025-03-01
- ids.document: 100000012
- ids.tracing: hash-C74FA395194D522CD1BEF9C6CEE042BD3254D23E0F7C516A5B4B9138D4648494
- obj.clause-number: 8.1.2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### R119: Attributes (heading)
- bib.al.original-language: en
- bib.dp.publication-date: 2025-03-01
- ids.document: 100000012
- obj.clause-number: 8.2
- obj.element-name: heading
- obj.language: en
- obj.specobject-type: heading
- ChapterName: 8.2 Attributes

#### R120: Information on the provision (SpecObject) (heading)
- bib.al.original-language: en
- bib.dp.publication-date: 2025-03-01
- ids.document: 100000012
- obj.clause-number: 8.2.1
- obj.element-name: heading
- obj.language: en
- obj.specobject-type: heading
- ChapterName: 8.2.1 Information on the provision (SpecObject)

##### R121: Content attributes on the provision (SpecObject) (heading)
- bib.al.original-language: en
- bib.dp.publication-date: 2025-03-01
- ids.document: 100000012
- obj.clause-number: 8.2.1.1
- obj.element-name: heading
- obj.language: en
- obj.specobject-type: heading
- ChapterName: 8.2.1.1 Content attributes on the provision (SpecObject)

###### prov-100000012-95d872ecc094429: Content attributes on the provision (SpecObject) (provision)
Content attributes see Table 1.
- bib.al.original-language: en
- bib.dp.publication-date: 2025-03-01
- ids.document: 100000012
- ids.tracing: hash-D37FF138866C33175C62EE7B3F12F5EE64191713A49DCA30B2C48AA1E65955A8
- obj.clause-number: 8.2.1.1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-33bae97efe26472

###### prov-100000012-33bae97efe26472: Content attributes (provision)
Table 1 — Content attributes
| data field term | ReqIF™ attribute name | ReqIF™ data type | occurrence | values | default | is-editable | location |  |  |  | definition | example |
| --- | --- | --- | --- | --- | --- | --- | --- | --- | --- | --- | --- | --- |
| data field term | ReqIF™ attribute name | ReqIF™ data type | occurrence | values | default | is-editable | document | heading | provision | specification | definition | example |
| Content | ReqIF.Text (content) | xhtml (32768) | zero or one | ~ | ~ | False | x |  | x |  | content of the SpecObject itself | ~ |
| Heading | ReqIF.ChapterName (heading) | xhtml (32768) | zero or one | ~ | ~ | False |  | x |  |  | content of the heading to the SpecObject | 1 Scope |
- bib.al.original-language: en
- bib.dp.publication-date: 2025-03-01
- ids.document: 100000012
- ids.tracing: hash-10CE27741D0706E4E245BF1913CA7950B0DB24DFE5F7B5233C33D338856413E0
- obj.clause-number: Table 1
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### R124: Object attributes on the provision (SpecObject) (heading)
- bib.al.original-language: en
- bib.dp.publication-date: 2025-03-01
- ids.document: 100000012
- obj.clause-number: 8.2.1.2
- obj.element-name: heading
- obj.language: en
- obj.specobject-type: heading
- ChapterName: 8.2.1.2 Object attributes on the provision (SpecObject)

###### prov-100000012-19dc73823c82460: Object attributes on the provision (SpecObject) (provision)
Object attributes see Table 2.
- bib.al.original-language: en
- bib.dp.publication-date: 2025-03-01
- ids.document: 100000012
- ids.tracing: hash-62E543000E713AD5A5A8970490D75438744B4C575175C22C3780DCC4A407CBC3
- obj.clause-number: 8.2.1.2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-fca44e790b7f458

###### prov-100000012-fca44e790b7f458: Object attributes (provision)
Table 2 — Object attributes
| data field term | ReqIF™ attribute name | ReqIF™ data type | occurrence | values | default | is-editable | location |  |  |  | definition | example |
| --- | --- | --- | --- | --- | --- | --- | --- | --- | --- | --- | --- | --- |
| data field term | ReqIF™ attribute name | ReqIF™ data type | occurrence | values | default | is-editable | document | heading | provision | specification | definition | example |
| Clause context | obj.clause-number | string-64 | zero or one | ~ | ~ | false |  | x | x |  | label of the context like annex, clause, figure, or table if this is labelled or numbered | 1 |
| Clause heading | obj.clause-heading | string-1024 | zero or one | ~ | ~ | false |  | x | x |  | heading of an annex, clause, figure, or table if specified the text without the label or number | Scope |
| Reliability | obj.conversion-reliability | integer-percentage | one | ~ | ~ | false |  |  | x |  | estimated reliability of the automatic pre-classification in percent (0 % to 100 %) | 92 |
| Standard element | obj.element-name | enum-single | zero or one | 8.3.1 | ~ | true |  | x | x |  | role of the provision in a standard document, i. e. name of the element according to ISO/IEC Directives, Part 2 | warning |
| Language | obj.language | enum-single | one | 8.3.2 | ~ | true |  | x | x |  | language of the provision, expressed as lower-case 2-letter language code according to ISO 639 | en |
| Modality; bindingness | obj.modality | enum-single | zero or one | 8.3.3 | ~ | true |  |  | x |  | level of obligation for a governing provision in the standard model | requirement |
| Normativity; context status | obj.normativity | enum-single | one | 8.3.4 | ~ | true |  |  | x |  | normative or informative status for the context of a provision in the standard model | normative |
| SpecObject type | obj.specobject-type | enum-single | one | 8.3.5 | ~ | true | x | x | x |  | workaround for target systems which do not support different SpecObject types | content |
| Conversion issues | obj.transformation-issues | string-1024 | ~ | ~ | ~ | false | x | x | x | x | conversion issues generated by the supplier | not annotated |
- bib.al.original-language: en
- bib.dp.publication-date: 2025-03-01
- ids.document: 100000012
- ids.tracing: hash-A84DB9B77739D7391874A274D38FF61355D0A94F4FCA13189C71264762894FE2
- obj.clause-number: Table 2
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R141
- cross-reference -> R144
- cross-reference -> R147
- cross-reference -> R150
- cross-reference -> R153

##### R127: Use attributes for intra-company management of the provision (SpecObject) (heading)
- bib.al.original-language: en
- bib.dp.publication-date: 2025-03-01
- ids.document: 100000012
- obj.clause-number: 8.2.1.3
- obj.element-name: heading
- obj.language: en
- obj.specobject-type: heading
- ChapterName: 8.2.1.3 Use attributes for intra-company management of the provision (SpecObject)

###### prov-100000012-f8eec1d9e5694ed: Use attributes for intra-company management of the provision (SpecObject) (provision)
Use attributes see Table 3.
- bib.al.original-language: en
- bib.dp.publication-date: 2025-03-01
- ids.document: 100000012
- ids.tracing: hash-4257B0B0A479509EFAD9E7B05808BBB931B033DCF95C969D54A645EA21E5FF9D
- obj.clause-number: 8.2.1.3
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-380de175be344eb

###### prov-100000012-380de175be344eb: Use attributes (provision)
Table 3 — Use attributes
| data field term | ReqIF™ attribute name | ReqIF™ data type | occurrence | values | default | is-editable | location |  |  |  | definition | example |
| --- | --- | --- | --- | --- | --- | --- | --- | --- | --- | --- | --- | --- |
| data field term | ReqIF™ attribute name | ReqIF™ data type | occurrence | values | default | is-editable | document | heading | provision | specification | definition | example |
| Business process | use.business-process | enum-multi | zero or more | 8.3.6 | ~ | true |  |  | x |  | applicable business process where the provision is relevant | production; supporting – technology development |
| Business sector; industry sector | use.business-sector | enum-multi | zero or more | 8.3.7 | ~ | true |  |  | x |  | industry sector; applicable business sector where the provision is relevant | industrials – mechanical engineering |
| Date usage begins | use.date-usage-begins | string-64 | zero or one | ~ | ~ | true |  |  | x |  | applicable date when implementation of the provision is going to begin, expressed in the format YYYY-MM-DD according to DIN ISO 8601-1 | 2024-01-01 |
| Date usage ends | use.date-usage-ends | string-64 | zero or one | ~ | ~ | true |  |  | x |  | applicable date when implementation of the provision may terminate, expressed in the format YYYY-MM-DD according to DIN ISO 8601-1 | 2027-12-31 |
| Interaction | use.interaction | enum-multi | zero or one | 8.3.8 | ~ | true |  |  | x |  | type of interaction of the provision in the standard or use model | integral aspect |
| Implementation region | use.location | enum-multi | zero or more | 8.3.9 | ~ | true |  |  | x |  | geological locations where the provision is going to be implemented, expressed as lower-case ALPHA-3 country code according to DIN EN ISO 3166-1 | eee; usa |
| Project phase | use.project-phase | enum-multi | zero or more | 8.3.10 | ~ | true |  |  | x |  | applicable project phase where the provision is relevant | definition and planning; execution |
| Product category | use.product-category | string-1024 | zero or more | ~ | ~ | true |  |  | x |  | product group; product sector; applicable product category where the provision is relevant | roller bearings |
| Product life cycle | use.product-life-cycle | enum-multi | zero or more | 8.3.11 | ~ | true |  |  | x |  | phase (superseded); applicable phase in the life cycle of a product where the provision is relevant | design; recycling |
| Purpose; intention; focus | use.purpose | enum-multi | zero or more | 8.3.12 | ~ | true |  |  | x |  | function (superseded); primary scope of the provision | safety |
- bib.al.original-language: en
- bib.dp.publication-date: 2025-03-01
- ids.document: 100000012
- ids.tracing: hash-E3051B9F1EB5F97F7BDB423B4C987E012F281FFF15834C6A1EBD189015B559D7
- obj.clause-number: Table 3
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R156
- cross-reference -> R159
- cross-reference -> R162
- cross-reference -> R165
- cross-reference -> R168
- cross-reference -> R171
- cross-reference -> R174

##### R130: Bibliographic document metadata (Perinorm 1.000) (heading)
- bib.al.original-language: en
- bib.dp.publication-date: 2025-03-01
- ids.document: 100000012
- obj.clause-number: 8.2.1.4
- obj.element-name: heading
- obj.language: en
- obj.specobject-type: heading
- ChapterName: 8.2.1.4 Bibliographic document metadata (Perinorm 1.000)

###### prov-100000012-da7b9612d006484: Bibliographic document metadata (Perinorm 1.000) (provision)
Bibliographic document metadata see Table 4.
- bib.al.original-language: en
- bib.dp.publication-date: 2025-03-01
- ids.document: 100000012
- ids.tracing: hash-7EFECEADC7571D7610046EC6D8795B23DBCB5BC46AEDAE157280051904B3BE98
- obj.clause-number: 8.2.1.4
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-a0e230da34dd408

###### prov-100000012-a0e230da34dd408: Bibliographic document metadata (provision)
Table 4 — Bibliographic document metadata
| data field term | ReqIF™ attribute name | ReqIF™ data type | occurrence | values | default | is-editable | location |  |  |  | definition | example |
| --- | --- | --- | --- | --- | --- | --- | --- | --- | --- | --- | --- | --- |
| data field term | ReqIF™ attribute name | ReqIF™ data type | occurrence | values | default | is-editable | document | heading | provision | specification | definition | example |
| a Metadata Field Specification |  |  |  |  |  |  |  |  |  |  |  |  |
| Document identifier | bib.di.document-identifier | string-1024 | one | ^a | ~ | false | x | x | x |  | document number as given in the Perinorm sources like the DITR database | ISO 1463 |
| Publication date | bib.dp.publication-date | string-64 | zero or one | ^a | ~ | false | x | x | x |  | publication date | 1982-07-00 |
| Update flag | bib.up.update-flag | string-1024 | one | ^a | ~ | false | x |  | x |  | update flag from Perinorm | ~ |
| Document type | bib.ts.document-type | string-64 | one | ^a | ~ | false | x |  | x |  | document type in Perinorm stage codes | ST*N |
| Title (German) | bib.tg.title-german | xhtml (2048) | zero or one | ^a | ~ | false | x |  | x |  | title in German language | Metall- und Oxidschichten – Schichtdickenmessung – Mikroskopisches Verfahren |
| Title (English) | bib.ti.title-english | xhtml (2048) | zero or one | ^a | ~ | false | x |  | x |  | title in English language | Metallic and oxide coatings – Measurement of coating thickness – Microscopical method |
| Title (French) | bib.tf.title-french | xhtml (2048) | zero or one | ^a | ~ | false | x |  | x |  | title in French language | Revêtements métalliques et couches d’oxydes – Mesurage de l’épaisseur – Méthode par coupe micrographique |
| Replaced by | bib.rx.replaced-by | string-16384 | one | ^a | ~ | false | x |  | x |  | document is replaced by newer edition | ISO 1463 (2003-03) |
| Replaces | bib.rz.replaces | string-16384 | zero or one | ^a | ~ | false | x |  | x |  | document replaces previous edition | ISO 1463 (1973-02) |
| Amended by | bib.az.amended-by | string-16384 | zero or one | ^a | ~ | false | x |  | x |  | document is amended by newer edition | ~ |
| Amends | bib.as.amends | string-16384 | zero or one | ^a | ~ | false | x |  | x |  | document amends previous edition | ~ |
| Classification | bib.ca.classification | string-1024 | zero or one | ^a | ~ | false | x |  | x |  | classification like ICS, UDC, DK, ISBN, or others | ICS 17.040.20 Properties of surfaces*ICS 25.220.40 Metallic coatings |
| Original language | bib.al.original-language | string-1024 | one | ^a | ~ | false | x |  | x |  | language of the original publication | en |
| Descriptors (German) | bib.ct.descriptors-german | string-16384 | zero or one | ^a | ~ | false | x |  | x |  | keywords in German language | Metallschicht*Methode*Prüfung*Schichtdickenmessung*Überzug*Design*Begriffe*Oxidschicht*Untersuchungsergebnis*Maß*Prüfergebn… |
| Descriptors (English) | bib.et.descriptors-english | string-16384 | zero or one | ^a | ~ | false | x |  | x |  | keywords in English language | Materials testing*Microscopic analysis*Microscopes*Test results*Layer thickness measurement*Processes*Oxide coatings*Coatings*Meas… |
| Descriptors (French) | bib.ft.descriptors-french | string-16384 | zero or one | ^a | ~ | false | x |  | x |  | keywords in French language | Procédure d’étalonnage*Mesure de l’épaisseur du revêtement*Email vitrifié*Email de porcelaine*Revêtement métallique*Présentation*Es… |
| International relationship | bib.ii.international-relationship | string-16384 | zero or one | ^a | ~ | false | x |  | x |  | international relationship to other publications | EN ISO 1463 (1994-10), IDT*ISO 1463 (1982-07), IDT*ISO/DIS 1463 (1999-09), IDT*SN EN ISO 1463 (1995), IDT*TS 1542 EN ISO 1463 EN ISO 14 … |
- bib.al.original-language: en
- bib.dp.publication-date: 2025-03-01
- ids.document: 100000012
- ids.tracing: hash-C3B2E0DFB24BD42E72A4CF8BE17808BE3F68095732C1CD248A8C12FB4A1E3F96
- obj.clause-number: Table 4
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### R134: Identification (ID) attributes on the provision (SpecObject) (heading)
- bib.al.original-language: en
- bib.dp.publication-date: 2025-03-01
- ids.document: 100000012
- obj.clause-number: 8.2.1.5
- obj.element-name: heading
- obj.language: en
- obj.specobject-type: heading
- ChapterName: 8.2.1.5 Identification (ID) attributes on the provision (SpecObject)

###### prov-100000012-be9ce0762f43461: Identification (ID) attributes on the provision (SpecObject) (provision)
Identification (ID) attributes see Table 5.
- bib.al.original-language: en
- bib.dp.publication-date: 2025-03-01
- ids.document: 100000012
- ids.tracing: hash-B7448A540DAD87AFD6928868522B04FF271EED3C49F513329C89695A0372CE7F
- obj.clause-number: 8.2.1.5
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-3ca5a24afb5a48f

###### prov-100000012-3ca5a24afb5a48f: Identification (ID) attributes (provision)
Table 5 — Identification (ID) attributes
| data field term | ReqIF™ attribute name | ReqIF™ data type | occurrence | values | default | is-editable | location |  |  |  | definition | example |
| --- | --- | --- | --- | --- | --- | --- | --- | --- | --- | --- | --- | --- |
| data field term | ReqIF™ attribute name | ReqIF™ data type | occurrence | values | default | is-editable | document | heading | provision | specification | definition | example |
| Document ID | ids.document | string-64 | zero or one | ~ | ~ | false | x | x | x |  | identifier which is unique for same version of the same document, e. g., using machine-resolvable database keys like the XML key (FIDAS key) | e11d82e5 |
| Element ID | ids.element | string-64 | zero or one | ~ | ~ | false |  | x | x |  | identifier which is unique for the same fragment within the same version of the same document, e. g., speaking identifiers (IDs) | fig-3a, sub-5.2.1, tab-na.1, … |
| Language-independent ID | ids.language-synoptic | string-64 | zero or one | ~ | ~ | false |  | x | x |  | identifier which is unique for the same fragment across all language variants within the same version of the same document | ~ |
| Version-independent tracing ID | ids.tracing | string-1024 | zero or one | ~ | ~ | false |  | x | x |  | identifier which is unique for the same content of the same fragment across all versions of the same document | fb53c22e-01b2-5dd7-98cb-bf2236977775 |
| XPath end | ids.xpath-end | string-1024 | zero or one | ~ | ~ | false |  |  | x |  | XPath into the XML source instance where the provision ends | /adoption[1]/adoption-front[1]/sec[1]/p[1] |
| XPath start | ids.xpath-start | string-1024 | zero or one | ~ | ~ | false |  |  | x |  | XPath into the XML source instance where the provision starts | /adoption[1]/adoption-front[1]/sec[1]/p[1] |
| Version-dependent unique ID | ids.unique | string-1024 | zero or one | ~ | ~ | false |  | x | x |  | identifier which is globally (GUID) or universally (UUID) unique for each fragment across all documents and versions of these | tr--e11d82e5--sub-3.2.1--42 |
- bib.al.original-language: en
- bib.dp.publication-date: 2025-03-01
- ids.document: 100000012
- ids.tracing: hash-2BBB60FC7903124938CAE79B66075086ADF6FF0CEBA77E360EDB4CBCEC495966
- obj.clause-number: Table 5
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### R137: Attributes on the document SpecObject for asset or service metadata of the creator, supplier, or publisher (heading)
- bib.al.original-language: en
- bib.dp.publication-date: 2025-03-01
- ids.document: 100000012
- obj.clause-number: 8.2.2
- obj.element-name: heading
- obj.language: en
- obj.specobject-type: heading
- ChapterName: 8.2.2 Attributes on the document SpecObject for asset or service metadata of the creator, supplier, or publisher

##### prov-100000012-c94fde6ee4f7407: Attributes on the document SpecObject for asset or service metadata of the creator, supplier, or publisher (provision)
Attributes on the document SpecObject see Table 6.
- bib.al.original-language: en
- bib.dp.publication-date: 2025-03-01
- ids.document: 100000012
- ids.tracing: hash-CC2D9C7B8E9231CEBC68D64B10C588AB9221CCBA69806A609883A52869B64BE3
- obj.clause-number: 8.2.2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-9e7674954430480

##### prov-100000012-9e7674954430480: Attributes on the document SpecObject (provision)
Table 6 — Attributes on the document SpecObject
| data field term | ReqIF™ attribute name | ReqIF™ data type | occurrence | values | default | is-editable | location |  |  |  | definition | example |
| --- | --- | --- | --- | --- | --- | --- | --- | --- | --- | --- | --- | --- |
| data field term | ReqIF™ attribute name | ReqIF™ data type | occurrence | values | default | is-editable | document | heading | provision | specification | definition | example |
| Originator | pub.originator | string-64 | one or more | ~ | ~ | false | x |  |  |  | abbreviation or short name of the originator, for example DIN, DKE, etc. | DIN*DKE*IEC*ISO |
| Harmonization | pub.harmonization | string-64 | one | ~ |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 example | false | x |  |  |  | harmonization string for the level of harmonization and version number | IDiS ReqIF™ interpretation for public standards 1.3 |
| Software | pub.software | string-64 | zero or one | ~ |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 example | false | x |  |  |  | identification string for software + version | X-Swift sts2reqif-42.17.4 |
| Supplier | pub.supplier | string-64 | one or more | ~ | ~ | false | x |  |  |  | abbreviation or short name of the supplier, for example DIN Media, VDE VERLAG, etc. | - DIN Media - VDE VERLAG |
- bib.al.original-language: en
- bib.dp.publication-date: 2025-03-01
- ids.document: 100000012
- ids.tracing: hash-9B2D8AC790AB5AE7C3123FC61178C7FC94F16D8AC0B14743451F4AD154C1145F
- obj.clause-number: Table 6
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### R140: Lists of attribute values (heading)
- bib.al.original-language: en
- bib.dp.publication-date: 2025-03-01
- ids.document: 100000012
- obj.clause-number: 8.3
- obj.element-name: heading
- obj.language: en
- obj.specobject-type: heading
- ChapterName: 8.3 Lists of attribute values

#### R141: Standard element (obj.element-name) (heading)
- bib.al.original-language: en
- bib.dp.publication-date: 2025-03-01
- ids.document: 100000012
- obj.clause-number: 8.3.1
- obj.element-name: heading
- obj.language: en
- obj.specobject-type: heading
- ChapterName: 8.3.1 Standard element (obj.element-name)

##### prov-100000012-1e3345e163cd4b2: Standard element (obj.element-name) (provision)
Attribute values see Table 7.
- bib.al.original-language: en
- bib.dp.publication-date: 2025-03-01
- ids.document: 100000012
- ids.tracing: hash-C970F16381E097E04E69CE172EF420722FA4C7281BBF9FE5E6FAC91576F39C5E
- obj.clause-number: 8.3.1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-4ec453639ad5441

##### prov-100000012-4ec453639ad5441: Values for the attribute obj.element-name (provision)
Table 7 — Values for the attribute obj.element-name
| values | definition |
| --- | --- |
| block | block with boxed text within a publication |
| caption | caption within a figure or table |
| concept | concept, i. e. container with terms and definition according to DIN ISO 10241-1 |
| descriptive-list | descriptive list (<dl> type enumeration) |
| display-formula | displayed formula |
| document | document, indicates that no other element could be determined |
| example | example |
| figure | figure (with caption) |
| footnote | footnote |
| formula | formula, i. e. inline formula signs or units) |
| graphics | graphics (without caption) |
| heading | heading of an annex, clause, or other type of division |
| legend | legend within a figure |
| list-of-documents | list of documents in the Normative References or Bibliography |
| note | note |
| ordered-list | ordered list (<ol> type enumeration) |
| ordering-details | ordering details (designation system) |
| paragraph | paragraph |
| printed-form | printed form |
| profile | metadata or title page |
| quotation | quotation, i. e. displayed text quoted from another source |
| signature | signature within a legal standard |
| standard-designation | standard designation (designation system) |
| table | table (with caption) |
| tabular-form | tabular form or informal table (without caption) |
| typed-form | typed form, i. e. computer code or typewriter text (monospaced) |
| undefined | default option if required and no value has been provided |
| units | units within a figure or table |
| unordered-list | unordered list (<ul> type enumeration) |
| warning | Warning |
- bib.al.original-language: en
- bib.dp.publication-date: 2025-03-01
- ids.document: 100000012
- ids.tracing: hash-B1A7ADDB7F481F9AB2DB2DE388D40555F3C82B1340FF5D5D0767C0045ABD2123
- obj.clause-number: Table 7
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### R144: Language (obj.language) (heading)
- bib.al.original-language: en
- bib.dp.publication-date: 2025-03-01
- ids.document: 100000012
- obj.clause-number: 8.3.2
- obj.element-name: heading
- obj.language: en
- obj.specobject-type: heading
- ChapterName: 8.3.2 Language (obj.language)

##### prov-100000012-fa53615e44b34fd: Language (obj.language) (provision)
Attribute values see Table 8.
- bib.al.original-language: en
- bib.dp.publication-date: 2025-03-01
- ids.document: 100000012
- ids.tracing: hash-1A1D004507F5F047F1A48C9AF4B4B68DE54FDEDB8C428EA5D9A67314F2199DE8
- obj.clause-number: 8.3.2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-78f49b51805e472

##### prov-100000012-78f49b51805e472: Values for the attribute obj.language (provision)
Table 8 — Values for the attribute obj.language
| values | definition |
| --- | --- |
| ar | Arabic |
| be | Belarusian |
| bg | Bulgarian |
| bs | Bosnian |
| cs | Czech |
| da | Danish |
| de | German |
| el | Greek, modern ~ |
| en | English |
| es | Spanish, Castilian |
| et | Estonian |
| fi | Finnish |
| fr | French |
| ga | Irish |
| he | Hebrew |
| hr | Croatian |
| hu | Hungarian |
| id | Indonesian |
| is | Icelandic |
| it | Italian |
| ja | Japanese |
| ka | Georgian |
| ko | Korean |
| lb | Luxembourgish, Letzeburgesch |
| lt | Lithuanian |
| lv | Latvian |
| mk | Macedonian |
| mt | Maltese |
| nl | Dutch, Flemish |
| no | Norwegian |
| pl | Polish |
| pt | Portuguese |
| ro | Romanian, Moldavian, Moldovan |
| ru | Russian |
| sk | Slovak |
| sl | Slovenian |
| sq | Albanian |
| sr | Serbian |
| sv | Swedish |
| tr | Turkish |
| uk | Ukrainian |
| undefined | default option if required and no value has been provided |
| vi | Vietnamese |
| zh | Chinese |
- bib.al.original-language: en
- bib.dp.publication-date: 2025-03-01
- ids.document: 100000012
- ids.tracing: hash-29A583D48F98683E266090F424923308CF04D65794A7A94773DDBD121E3419C0
- obj.clause-number: Table 8
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### R147: Modality; bindingness (obj.modality) (heading)
- bib.al.original-language: en
- bib.dp.publication-date: 2025-03-01
- ids.document: 100000012
- obj.clause-number: 8.3.3
- obj.element-name: heading
- obj.language: en
- obj.specobject-type: heading
- ChapterName: 8.3.3 Modality; bindingness (obj.modality)

##### prov-100000012-cd79d484f11640f: Modality; bindingness (obj.modality) (provision)
Attribute values see Table 9.
- bib.al.original-language: en
- bib.dp.publication-date: 2025-03-01
- ids.document: 100000012
- ids.tracing: hash-5F739EEEB7DA445A6B24F75AC58E74979FB92BCE6902B09B06A48BBA599C4618
- obj.clause-number: 8.3.3
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-fbee9246e358411

##### prov-100000012-fbee9246e358411: Values for the attribute obj.modality (provision)
Table 9 — Values for the attribute obj.modality
| values | definition |
| --- | --- |
| ambiguous | modality is ambiguous, e. g., there are multiple or unclear variant occurrences for the modality |
| capability | expression that conveys the ability, fitness, or quality necessary to do or achieve a specified thing (ISO/IEC Directives, Part 2) |
| constraint | external constraint or obligation on the user of the document that is not stated as a provision of the document, e. g., laws of nature or particular conditions existing in some countries or regions (ISO/IEC Directives, Part 2) |
| permission | expression that conveys consent or liberty (or opportunity) to do something (ISO/IEC Directives, Part 2) |
| possibility | expression that conveys expected or conceivable material, physical or causal outcome (ISO/IEC Directives, Part 2) |
| recommendation | expression that conveys a suggested possible choice or course of action deemed to be particularly suitable without necessarily mentioning or excluding others (ISO/IEC Directives, Part 2) |
| requirement | expression that conveys objectively verifiable criteria to be fulfilled and from which no deviation is permitted if conformance with the document is to be claimed (ISO/IEC Directives, Part 2) |
| undefined | modality is undefined, e. g., modality of the provision has not been explicitly evaluated |
- bib.al.original-language: en
- bib.dp.publication-date: 2025-03-01
- ids.document: 100000012
- ids.tracing: hash-3E7BA527615CADF99353018F3C37F6F04848D0E1066F6DD162A4B0BDDCF719C1
- obj.clause-number: Table 9
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### R150: Normativity; context status (obj.normativity) (heading)
- bib.al.original-language: en
- bib.dp.publication-date: 2025-03-01
- ids.document: 100000012
- obj.clause-number: 8.3.4
- obj.element-name: heading
- obj.language: en
- obj.specobject-type: heading
- ChapterName: 8.3.4 Normativity; context status (obj.normativity)

##### prov-100000012-885287eb12d24c1: Normativity; context status (obj.normativity) (provision)
Attribute values see Table 10.
- bib.al.original-language: en
- bib.dp.publication-date: 2025-03-01
- ids.document: 100000012
- ids.tracing: hash-753EED96FFA2619C684D503EC54FFD1B21165FE948C74F0F0FA2ADF245A369F5
- obj.clause-number: 8.3.4
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-e90b3b8b758e46b

##### prov-100000012-e90b3b8b758e46b: Values for the attribute obj.normativity (provision)
Table 10 — Values for the attribute obj.normativity
| values | definition |
| --- | --- |
| informative | context is an informative element, e. g., annex (informative), example, foreword, introduction, note |
| normative | context is a normative element, e. g., annex (normative) |
| undefined | default option if required and no value has been provided |
- bib.al.original-language: en
- bib.dp.publication-date: 2025-03-01
- ids.document: 100000012
- ids.tracing: hash-9BDF9597329CC072594C992DCF4141294C0831E1E4E4DF04A0FEEC676F97D52F
- obj.clause-number: Table 10
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### R153: SpecObject type (obj.specobj-type) (heading)
- bib.al.original-language: en
- bib.dp.publication-date: 2025-03-01
- ids.document: 100000012
- obj.clause-number: 8.3.5
- obj.element-name: heading
- obj.language: en
- obj.specobject-type: heading
- ChapterName: 8.3.5 SpecObject type (obj.specobj-type)

##### prov-100000012-ff4f033e953945f: SpecObject type (obj.specobj-type) (provision)
Attribute values see Table 11.
- bib.al.original-language: en
- bib.dp.publication-date: 2025-03-01
- ids.document: 100000012
- ids.tracing: hash-9215B6AEF255FCFB4AC84B110615F1C19D4D7D1C323421D8DA99D642EC1D86A8
- obj.clause-number: 8.3.5
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-b4c07446ee7e42c

##### prov-100000012-b4c07446ee7e42c: Values for the attribute obj.specobj-type (provision)
Table 11 — Values for the attribute obj.specobj-type
| values | definition |
| --- | --- |
| document | content of the profile to the SpecObject (title page) |
| heading | content of the heading to the SpecObject |
| provision | content of the SpecObject itself |
| undefined | default option if required and no value has been provided |
- bib.al.original-language: en
- bib.dp.publication-date: 2025-03-01
- ids.document: 100000012
- ids.tracing: hash-3B55A4B904143C5E54CD6176FF731BD95D808BBA2837B87411F123B0F6C491AB
- obj.clause-number: Table 11
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### R156: Business process (use.business-process) (heading)
- bib.al.original-language: en
- bib.dp.publication-date: 2025-03-01
- ids.document: 100000012
- obj.clause-number: 8.3.6
- obj.element-name: heading
- obj.language: en
- obj.specobject-type: heading
- ChapterName: 8.3.6 Business process (use.business-process)

##### prov-100000012-3874bbbec47d4ba: Business process (use.business-process) (provision)
Attribute values see Table 12.
- bib.al.original-language: en
- bib.dp.publication-date: 2025-03-01
- ids.document: 100000012
- ids.tracing: hash-170A868CA3BC6DE8ECF22BF57BFF0CFB272D89E3AAFC71595A37C5AFCA32C178
- obj.clause-number: 8.3.6
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-b1bc8ec276884ff

##### prov-100000012-b1bc8ec276884ff: Values for the attribute use-business-process (provision)
Table 12 — Values for the attribute use-business-process
| values | definition |
| --- | --- |
| logistics external | logistics outbound; activities deliver your product or service to your customer; these are things like collection, storage, and distribution systems, and they may be internal or external to your organization [9] |
| logistics internal | logistics inbound; processes related to receiving, storing, and distributing inputs internally; your supplier relationships are a key factor in creating value here [9] |
| marketing and sales | processes you use to persuade clients to purchase from you instead of your competitors; the benefits you offer, and how well you communicate them, are sources of value here [9] |
| production | operations; transformation activities that change inputs into outputs that are sold to customers; here, your operational systems create value [9] |
| service | activities related to maintaining the value of your product or service to your customers, once it’s been purchased [9] |
| supporting – acquisition | purchasing processes |
| supporting – corporate infrastructure | infrastructure |
| supporting – human resource management | personal department processes |
| supporting – technology development | development |
| undefined | default option if required and no value has been provided |
- bib.al.original-language: en
- bib.dp.publication-date: 2025-03-01
- ids.document: 100000012
- ids.tracing: hash-EC8B4BAA53CAC0E1DBF798E6372DE2EAFC922D484AEE0B8FF16824B3A9E98F67
- obj.clause-number: Table 12
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-996957e8ccc24fe

#### R159: Business sector; industry sector (use.business-sector) (heading)
- bib.al.original-language: en
- bib.dp.publication-date: 2025-03-01
- ids.document: 100000012
- obj.clause-number: 8.3.7
- obj.element-name: heading
- obj.language: en
- obj.specobject-type: heading
- ChapterName: 8.3.7 Business sector; industry sector (use.business-sector)

##### prov-100000012-489c71e10f214fd: Business sector; industry sector (use.business-sector) (provision)
Attribute values see Table 13.
- bib.al.original-language: en
- bib.dp.publication-date: 2025-03-01
- ids.document: 100000012
- ids.tracing: hash-510AE4E231BCB8703ECE327F323B8566D4AD8AA69AAFBA9C987F690BC43DE8E4
- obj.clause-number: 8.3.7
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-1d17f14e27de4c3

##### prov-100000012-1d17f14e27de4c3: Values for the attribute use.business-sector (provision)
Table 13 — Values for the attribute use.business-sector
| values | definition |
| --- | --- |
| building | building sector |
| consumer discretionary | consumer discretionary sector |
| consumer services | consumer services sector |
| consumer staples | consumer staples sector |
| energy | energy sector |
| financials | financials sector |
| healthcare | healthcare sector |
| industrials – aerospace | industrials – aerospace sector |
| industrials – automotive | industrials – automotive sector |
| industrials – defense | industrials – defense sector |
| industrials – electrical engineering | industrials – electrical engineering sector |
| industrials – mechanical engineering | industrials – mechanical engineering sector |
| industrials – medical engineering | industrials – medical engineering sector |
| materials | materials sector |
| other | other sector |
| real estate | real estate sector |
| services | services sector |
| technology | technology sector |
| undefined | default option if required and no value has been provided |
| utilities | utilities sector |
- bib.al.original-language: en
- bib.dp.publication-date: 2025-03-01
- ids.document: 100000012
- ids.tracing: hash-DDB20F4F512D682F029FAD1F618663D91D6C2C51B398B5912C38955FD615FF3D
- obj.clause-number: Table 13
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### R162: Interaction (use.interaction) (heading)
- bib.al.original-language: en
- bib.dp.publication-date: 2025-03-01
- ids.document: 100000012
- obj.clause-number: 8.3.8
- obj.element-name: heading
- obj.language: en
- obj.specobject-type: heading
- ChapterName: 8.3.8 Interaction (use.interaction)

##### prov-100000012-15e868c74b9040c: Interaction (use.interaction) (provision)
Attribute values see Table 14.
- bib.al.original-language: en
- bib.dp.publication-date: 2025-03-01
- ids.document: 100000012
- ids.tracing: hash-3B3955ADD0CDF3F13A2CB84430DF7733DBFECAB6CCE163B3544B2B9DD4A5C546
- obj.clause-number: 8.3.8
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-db55aa9cb5f34f9

##### prov-100000012-db55aa9cb5f34f9: Values for the attribute use.interaction (provision)
Table 14 — Values for the attribute use.interaction
| values | definition |
| --- | --- |
| activity | activity (process) |
| functional | functional (system) |
| integral aspect | integral aspect (system) |
| interface | interface (system) |
| undefined | default option if required and no value has been provided |
| verification | verification (method of proof) |
- bib.al.original-language: en
- bib.dp.publication-date: 2025-03-01
- ids.document: 100000012
- ids.tracing: hash-60A9F0CEA1D02A8D42AA48E29E00FB3BD01F5448D1F87A7EFB828324B1728ECC
- obj.clause-number: Table 14
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### R165: Implementation region (use.location) (heading)
- bib.al.original-language: en
- bib.dp.publication-date: 2025-03-01
- ids.document: 100000012
- obj.clause-number: 8.3.9
- obj.element-name: heading
- obj.language: en
- obj.specobject-type: heading
- ChapterName: 8.3.9 Implementation region (use.location)

##### prov-100000012-7f68f589a88b473: Implementation region (use.location) (provision)
Attribute values see Table 15.
- bib.al.original-language: en
- bib.dp.publication-date: 2025-03-01
- ids.document: 100000012
- ids.tracing: hash-8B9D3D29B07121BE654E914A9AA8D1A0A3AC568BAB24EC88CEAC2C11921690C5
- obj.clause-number: 8.3.9
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-28f0e72248f549d

##### prov-100000012-28f0e72248f549d: Values for the attribute use.location (provision)
Table 15 — Values for the attribute use.location
| values | definition |
| --- | --- |
| abb | Asia |
| alb | Albania |
| and | Andorra |
| atg | Antigua and Barbuda |
| aus | Australia |
| aut | Austria |
| bel | Belgium |
| bgr | Bulgaria |
| bhs | Bahamas |
| bih | Bosnia and Herzegovina |
| blr | Belarus |
| can | Canada |
| che | Switzerland |
| chn | China |
| cub | Cuba |
| cyp | Cyprus |
| cze | Czechia |
| deu | Germany |
| dnk | Denmark |
| eee | Europe |
| esp | Spain |
| est | Estonia |
| fff | Africa |
| fin | Finland |
| fra | France |
| gbr | United Kingdom of Great Britain and Northern Ireland |
| geo | Georgia |
| gib | Gibraltar |
| grc | Greece |
| hkg | China, Hong Kong Special Administrative Region |
| hrv | Croatia |
| hun | Hungary |
| idn | Indonesia |
| ind | India |
| irl | Ireland |
| isl | Iceland |
| isr | Israel |
| ita | Italy |
| jam | Jamaica |
| jpn | Japan |
| kgz | Kyrgyzstan |
| kor | Republic of Korea |
| kwt | Kuwait |
| lie | Liechtenstein |
| ltu | Lithuania |
| lux | Luxembourg |
| lva | Latvia |
| mco | Monaco |
| mda | Republic of Moldova |
| mkd | North Macedonia |
| mlt | Malta |
| mne | Montenegro |
| nld | The Netherlands |
| nnn | North America |
| nor | Norway |
| nzl | New Zealand |
| phl | Philippines |
| pol | Poland |
| prk | Democratic People’s Republic of Korea |
| prt | Portugal |
| rou | Romania |
| rus | Russian Federation |
| sau | Saudi Arabia |
| srb | Serbia |
| srr | South America |
| svk | Slovakia |
| svn | Slovenia |
| swe | Sweden |
| tjk | Tajikistan |
| tur | Türkiye; Turkey |
| twn | Taiwan (Province of China) |
| ukr | Ukraine |
| undefined | default option if required and no value has been provided |
| usa | United States of America |
| uuu | Oceania |
| vnm | Viet Nam; Vietnam |
| xkk | Kosovo |
- bib.al.original-language: en
- bib.dp.publication-date: 2025-03-01
- ids.document: 100000012
- ids.tracing: hash-849A1A143E0EA4F3AACB1AED734A645595AD00D214F340A7C41C04930A5079A2
- obj.clause-number: Table 15
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### R168: Project phase (use.project-phase) (heading)
- bib.al.original-language: en
- bib.dp.publication-date: 2025-03-01
- ids.document: 100000012
- obj.clause-number: 8.3.10
- obj.element-name: heading
- obj.language: en
- obj.specobject-type: heading
- ChapterName: 8.3.10 Project phase (use.project-phase)

##### prov-100000012-c3b5f14ea73d43d: Project phase (use.project-phase) (provision)
Attribute values see Table 16.
- bib.al.original-language: en
- bib.dp.publication-date: 2025-03-01
- ids.document: 100000012
- ids.tracing: hash-1E401D363ABC371E66EB7575AC22BD87A3BDC44992437C151C7BD34861FC25C8
- obj.clause-number: 8.3.10
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-f8b474a7f0ce478

##### prov-100000012-f8b474a7f0ce478: Values for the attribute use.project-phase (provision)
Table 16 — Values for the attribute use.project-phase
| Values | definition |
| --- | --- |
| close out | analyze and summarize the results to close out of the project |
| definition and planning | define tasks and timelines needed to execute the project |
| Execution | execute the project plan |
| Initiation | define project objectives, deadlines, priorities, chances, and risks |
| monitoring and control | monitor and control of the project progress |
| Undefined | default option if required and no value has been provided |
- bib.al.original-language: en
- bib.dp.publication-date: 2025-03-01
- ids.document: 100000012
- ids.tracing: hash-EC01FCB126EEBBAA6CD141885AD83A7E455C7FF7E9B803588DAF5129AC8FF8C6
- obj.clause-number: Table 16
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### R171: Product life cycle (use.product-life-cycle) (heading)
- bib.al.original-language: en
- bib.dp.publication-date: 2025-03-01
- ids.document: 100000012
- obj.clause-number: 8.3.11
- obj.element-name: heading
- obj.language: en
- obj.specobject-type: heading
- ChapterName: 8.3.11 Product life cycle (use.product-life-cycle)

##### prov-100000012-05ab8d1961ea46f: Product life cycle (use.product-life-cycle) (provision)
Attribute values see Table 17.
- bib.al.original-language: en
- bib.dp.publication-date: 2025-03-01
- ids.document: 100000012
- ids.tracing: hash-5FA41D0E30FB2458F81C3D5BFE6982A50948BB55962E544C3C542CB54D3CC4D3
- obj.clause-number: 8.3.11
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-e7b927faf9ab468

##### prov-100000012-e7b927faf9ab468: Values for the attribute use.product-life-cycle (provision)
Table 17 — Values for the attribute use.product-life-cycle
| values | definition |
| --- | --- |
| design | design of a product |
| maintenance | maintenance or service for a product |
| realization | realization of a product |
| recycling | disposal or recycling of a product |
| undefined | default option if required and no value has been provided |
| use phase | use phase for a product |
- bib.al.original-language: en
- bib.dp.publication-date: 2025-03-01
- ids.document: 100000012
- ids.tracing: hash-C3E30D52CDD71C212CC1A3F8D4A1325CDDFB45DD1D27FBB0FCF18C1499C711A4
- obj.clause-number: Table 17
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### R174: Purpose; intention; focus (use.purpose) (heading)
- bib.al.original-language: en
- bib.dp.publication-date: 2025-03-01
- ids.document: 100000012
- obj.clause-number: 8.3.12
- obj.element-name: heading
- obj.language: en
- obj.specobject-type: heading
- ChapterName: 8.3.12 Purpose; intention; focus (use.purpose)

##### prov-100000012-ca734d93269e4b3: Purpose; intention; focus (use.purpose) (provision)
Attribute values see Table 18.
- bib.al.original-language: en
- bib.dp.publication-date: 2025-03-01
- ids.document: 100000012
- ids.tracing: hash-94F2BCBA27E203BBE75EE5DE5DA5CD9EEE214CE00AF864127C8A049A198A38C2
- obj.clause-number: 8.3.12
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-b25142765245437

##### prov-100000012-b25142765245437: Values for the attribute use.purpose (provision)
Table 18 — Values for the attribute use.purpose
| values | definition |
| --- | --- |
| availability | provision serves availability |
| communication | provision serves communication; means informative |
| future proof | provision serves future-proof |
| health | provision serves health |
| interoperability | interoperability is a separate functionality |
| maintainability | provision serves maintainability |
| quality | provision serves quality |
| relation | provision shows connections, e. g., "Normative references“ |
| reliability | provision serves reliability |
| safety | provision serves safety |
| sustainability | provision serves sustainability |
| undefined | default option if required and no value has been provided |
- bib.al.original-language: en
- bib.dp.publication-date: 2025-03-01
- ids.document: 100000012
- ids.tracing: hash-0BEE393290558D1AF2A13C7B2722F70CA5249A0FF12EC69F803EE4FD653C9918
- obj.clause-number: Table 18
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### R177: Long name and identifier syntax (heading)
- bib.al.original-language: en
- bib.dp.publication-date: 2025-03-01
- ids.document: 100000012
- obj.clause-number: 8.4
- obj.element-name: heading
- obj.language: en
- obj.specobject-type: heading
- ChapterName: 8.4 Long name and identifier syntax

#### R178: Datatype definitions (DataTypeDefinitions) (heading)
- bib.al.original-language: en
- bib.dp.publication-date: 2025-03-01
- ids.document: 100000012
- obj.clause-number: 8.4.1
- obj.element-name: heading
- obj.language: en
- obj.specobject-type: heading
- ChapterName: 8.4.1 Datatype definitions (DataTypeDefinitions)

##### prov-100000012-f4ee6cbee102479: Datatype definitions (DataTypeDefinitions) (provision)
DataTypeDefinitions see Table 19.
- bib.al.original-language: en
- bib.dp.publication-date: 2025-03-01
- ids.document: 100000012
- ids.tracing: hash-C6F1E7070FBF77C49CAA45B79E0E3EF7C20D49B50E57740558966AF69842EDBD
- obj.clause-number: 8.4.1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-a89cb60e56ed499

##### prov-100000012-a89cb60e56ed499: DataTypeDefinitions (provision)
Table 19 — DataTypeDefinitions
| long name | identifier | class name | class name abbreviation |
| --- | --- | --- | --- |
| date | tr--ddd--date | DatatypeDefinitionDate | ddd |
| element-name | tr--dde--element-name | DatatypeDefinitionEnumeration | dde |
| block | tr--ev--element-name--block | EnumValue | ev |
| caption | tr--ev--element-name--caption | EnumValue | ev |
| concept | tr--ev--element-name--concept | EnumValue | ev |
| descriptive-list | tr--ev--element-name--descriptive-list | EnumValue | ev |
| display-formula | tr--ev--element-name--display-formula | EnumValue | ev |
| document | tr--ev--element-name--document | EnumValue | ev |
| example | tr--ev--element-name--example | EnumValue | ev |
| figure | tr--ev--element-name--figure | EnumValue | ev |
| footnote | tr--ev--element-name--footnote | EnumValue | ev |
| formula | tr--ev--element-name--formula | EnumValue | ev |
| graphics | tr--ev--element-name--graphics | EnumValue | ev |
| heading | tr--ev--element-name--heading | EnumValue | ev |
| legend | tr--ev--element-name--legend | EnumValue | ev |
| list-of-documents | tr--ev--element-name--list-of-documents | EnumValue | ev |
| note | tr--ev--element-name--note | EnumValue | ev |
| ordered-list | tr--ev--element-name--ordered-list | EnumValue | ev |
| ordering-details | tr--ev--element-name--ordering-details | EnumValue | ev |
| paragraph | tr--ev--element-name--paragraph | EnumValue | ev |
| printed-form | tr--ev--element-name--printed-form | EnumValue | ev |
| profile | tr--ev--element-name--profile | EnumValue | ev |
| quotation | tr--ev--element-name--quotation | EnumValue | ev |
| signature | tr--ev--element-name--signature | EnumValue | ev |
| standard-designation | tr--ev--element-name--standard-designation | EnumValue | ev |
| table | tr--ev--element-name--table | EnumValue | ev |
| tabular-form | tr--ev--element-name--tabular-form | EnumValue | ev |
| typed-form | tr--ev--element-name--typed-form | EnumValue | ev |
| undefined | tr--ev--element-name--undefined | EnumValue | ev |
| units | tr--ev--element-name--units | EnumValue | ev |
| unordered-list | tr--ev--element-name--unordered-list | EnumValue | ev |
| warning | tr--ev--element-name--warning | EnumValue | ev |
| integer | tr--ddi--integer | DatatypeDefinitionInteger | ddi |
| integer-percentage | tr--ddi--integer-percentage | DatatypeDefinitionInteger | ddi |
| language | tr--dde--language | DatatypeDefinitionEnumeration | dde |
| ar | tr--ev--language--ar | EnumValue | ev |
| be | tr--ev--language--be | EnumValue | ev |
| bg | tr--ev--language--bg | EnumValue | ev |
| bs | tr--ev--language--bs | EnumValue | ev |
| cs | tr--ev--language--cs | EnumValue | ev |
| da | tr--ev--language--da | EnumValue | ev |
| de | tr--ev--language--de | EnumValue | ev |
| el | tr--ev--language--el | EnumValue | ev |
| en | tr--ev--language--en | EnumValue | ev |
| es | tr--ev--language--es | EnumValue | ev |
| et | tr--ev--language--et | EnumValue | ev |
| fi | tr--ev--language--fi | EnumValue | ev |
| fr | tr--ev--language--fr | EnumValue | ev |
| ga | tr--ev--language--ga | EnumValue | ev |
| he | tr--ev--language--he | EnumValue | ev |
| hr | tr--ev--language--hr | EnumValue | ev |
| hu | tr--ev--language--hu | EnumValue | ev |
| id | tr--ev--language--id | EnumValue | ev |
| is | tr--ev--language--is | EnumValue | ev |
| it | tr--ev--language--it | EnumValue | ev |
| ja | tr--ev--language--ja | EnumValue | ev |
| ka | tr--ev--language--ka | EnumValue | ev |
| ko | tr--ev--language--ko | EnumValue | ev |
| lb | tr--ev--language--lb | EnumValue | ev |
| lt | tr--ev--language--lt | EnumValue | ev |
| lv | tr--ev--language--lv | EnumValue | ev |
| mk | tr--ev--language--mk | EnumValue | ev |
| mt | tr--ev--language--mt | EnumValue | ev |
| nl | tr--ev--language--nl | EnumValue | ev |
| no | tr--ev--language--no | EnumValue | ev |
| pl | tr--ev--language--pl | EnumValue | ev |
| pt | tr--ev--language--pt | EnumValue | ev |
| ro | tr--ev--language--ro | EnumValue | ev |
| ru | tr--ev--language--ru | EnumValue | ev |
| sk | tr--ev--language--sk | EnumValue | ev |
| sl | tr--ev--language--sl | EnumValue | ev |
| sq | tr--ev--language--sq | EnumValue | ev |
| sr | tr--ev--language--sr | EnumValue | ev |
| sv | tr--ev--language--sv | EnumValue | ev |
| tr | tr--ev--language--tr | EnumValue | ev |
| uk | tr--ev--language--uk | EnumValue | ev |
| undefined | tr--ev--language--undefined | EnumValue | ev |
| vi | tr--ev--language--vi | EnumValue | ev |
| zh | tr--ev--language--zh | EnumValue | ev |
| modality | tr--dde--modality | DatatypeDefinitionEnumeration | dde |
| ambiguous | tr--ev--modality--ambiguous | EnumValue | ev |
| capability | tr--ev--modality--capability | EnumValue | ev |
| constraint | tr--ev--modality--constraint | EnumValue | ev |
| permission | tr--ev--modality--permission | EnumValue | ev |
| possibility | tr--ev--modality--possibility | EnumValue | ev |
| recommendation | tr--ev--modality--recommendation | EnumValue | ev |
| requirement | tr--ev--modality--requirement | EnumValue | ev |
| undefined | tr--ev--modality--undefined | EnumValue | ev |
| normativity | tr--dde--normativity | DatatypeDefinitionEnumeration | dde |
| informative | tr--ev--normativity--informative | EnumValue | ev |
| normative | tr--ev--normativity--normative | EnumValue | ev |
| undefined | tr--ev--normativity--undefined | EnumValue | ev |
| specobject-type | tr--dde--specobject-type | DatatypeDefinitionEnumeration | dde |
| document | tr--ev--specobject-type--document | EnumValue | ev |
| heading | tr--ev--specobject-type--heading | EnumValue | ev |
| provision | tr--ev--specobject-type--provision | EnumValue | ev |
| undefined | tr--ev--specobject-type--undefined | EnumValue | ev |
| string-1024 | tr--dds--string-1024 | DatatypeDefinitionString | dds |
| string-16384 | tr--dds--string-16384 | DatatypeDefinitionString | dds |
| string-64 | tr--dds--string-64 | DatatypeDefinitionString | dds |
| string-date | tr--dds--string-date | DatatypeDefinitionString | dds |
| use.business-process | tr--dde--use.business-process | DatatypeDefinitionEnumeration | dde |
| logistics external | tr--ev--use.business-process--logistics-external | EnumValue | ev |
| logistics internal | tr--ev--use.business-process--logistics-internal | EnumValue | ev |
| marketing and sales | tr--ev--use.business-process--marketing-and-sales | EnumValue | ev |
| production | tr--ev--use.business-process--production | EnumValue | ev |
| service | tr--ev--use.business-process--service | EnumValue | ev |
| supporting – acquisition | tr--ev--use.business-process--supporting---acquisition | EnumValue | ev |
| supporting – corporate infrastructure | tr--ev--use.business-process--supporting---corporate-infrastructure | EnumValue | ev |
| supporting – human resource management | tr--ev--use.business-process--supporting---human-resource-management | EnumValue | ev |
| supporting – technology development | tr--ev--use.business-process--supporting---technology-development | EnumValue | ev |
| undefined | tr--ev--use.business-process--undefined | EnumValue | ev |
| use.business-sector | tr--dde--use.business-sector | DatatypeDefinitionEnumeration | dde |
| building | tr--ev--use.business-sector--building | EnumValue | ev |
| consumer discretionary | tr--ev--use.business-sector--consumer-discretionary | EnumValue | ev |
| consumer services | tr--ev--use.business-sector--consumer-services | EnumValue | ev |
| consumer staples | tr--ev--use.business-sector--consumer-staples | EnumValue | ev |
| energy | tr--ev--use.business-sector--energy | EnumValue | ev |
| financials | tr--ev--use.business-sector--financials | EnumValue | ev |
| healthcare | tr--ev--use.business-sector--healthcare | EnumValue | ev |
| industrials – aerospace | tr--ev--use.business-sector--industrials---aerospace | EnumValue | ev |
| industrials – automotive | tr--ev--use.business-sector--industrials---automotive | EnumValue | ev |
| industrials – defense | tr--ev--use.business-sector--industrials---defense | EnumValue | ev |
| industrials – electrical engineering | tr--ev--use.business-sector--industrials---electrical-engineering | EnumValue | ev |
| industrials – mechanical engineering | tr--ev--use.business-sector--industrials---mechanical-engineering | EnumValue | ev |
| industrials – medical engineering | tr--ev--use.business-sector--industrials---medical-engineering | EnumValue | ev |
| materials | tr--ev--use.business-sector--materials | EnumValue | ev |
| other | tr--ev--use.business-sector--other | EnumValue | ev |
| real estate | tr--ev--use.business-sector--real-estate | EnumValue | ev |
| services | tr--ev--use.business-sector--services | EnumValue | ev |
| technology | tr--ev--use.business-sector--technology | EnumValue | ev |
| undefined | tr--ev--use.business-sector--undefined | EnumValue | ev |
| utilities | tr--ev--use.business-sector--utilities | EnumValue | ev |
| use.interaction | tr--dde--use.interaction | DatatypeDefinitionEnumeration | dde |
| activity | tr--ev--use.interaction--activity | EnumValue | ev |
| functional | tr--ev--use.interaction--functional | EnumValue | ev |
| integral aspect | tr--ev--use.interaction--integral-aspect | EnumValue | ev |
| interface | tr--ev--use.interaction--interface | EnumValue | ev |
| undefined | tr--ev--use.interaction--undefined | EnumValue | ev |
| verification | tr--ev--use.interaction--verification | EnumValue | ev |
| use.location | tr--dde--use.location | DatatypeDefinitionEnumeration | dde |
| abb | tr--ev--use.location--abb | EnumValue | ev |
| alb | tr--ev--use.location--alb | EnumValue | ev |
| and | tr--ev--use.location--and | EnumValue | ev |
| atg | tr--ev--use.location--atg | EnumValue | ev |
| aus | tr--ev--use.location--aus | EnumValue | ev |
| aut | tr--ev--use.location--aut | EnumValue | ev |
| bel | tr--ev--use.location--bel | EnumValue | ev |
| bgr | tr--ev--use.location--bgr | EnumValue | ev |
| bhs | tr--ev--use.location--bhs | EnumValue | ev |
| bih | tr--ev--use.location--bih | EnumValue | ev |
| blr | tr--ev--use.location--blr | EnumValue | ev |
| can | tr--ev--use.location--can | EnumValue | ev |
| che | tr--ev--use.location--che | EnumValue | ev |
| chn | tr--ev--use.location--chn | EnumValue | ev |
| cub | tr--ev--use.location--cub | EnumValue | ev |
| cyp | tr--ev--use.location--cyp | EnumValue | ev |
| cze | tr--ev--use.location--cze | EnumValue | ev |
| deu | tr--ev--use.location--deu | EnumValue | ev |
| dnk | tr--ev--use.location--dnk | EnumValue | ev |
| eee | tr--ev--use.location--eee | EnumValue | ev |
| esp | tr--ev--use.location--esp | EnumValue | ev |
| est | tr--ev--use.location--est | EnumValue | ev |
| fff | tr--ev--use.location--fff | EnumValue | ev |
| fin | tr--ev--use.location--fin | EnumValue | ev |
| fra | tr--ev--use.location--fra | EnumValue | ev |
| gbr | tr--ev--use.location--gbr | EnumValue | ev |
| geo | tr--ev--use.location--geo | EnumValue | ev |
| gib | tr--ev--use.location--gib | EnumValue | ev |
| grc | tr--ev--use.location--grc | EnumValue | ev |
| hkg | tr--ev--use.location--hkg | EnumValue | ev |
| hrv | tr--ev--use.location--hrv | EnumValue | ev |
| hun | tr--ev--use.location--hun | EnumValue | ev |
| idn | tr--ev--use.location--idn | EnumValue | ev |
| ind | tr--ev--use.location--ind | EnumValue | ev |
| irl | tr--ev--use.location--irl | EnumValue | ev |
| isl | tr--ev--use.location--isl | EnumValue | ev |
| isr | tr--ev--use.location--isr | EnumValue | ev |
| ita | tr--ev--use.location--ita | EnumValue | ev |
| jam | tr--ev--use.location--jam | EnumValue | ev |
| jpn | tr--ev--use.location--jpn | EnumValue | ev |
| kgz | tr--ev--use.location--kgz | EnumValue | ev |
| kor | tr--ev--use.location--kor | EnumValue | ev |
| kos | tr--ev--use.location--kos | EnumValue | ev |
| kwt | tr--ev--use.location--kwt | EnumValue | ev |
| lie | tr--ev--use.location--lie | EnumValue | ev |
| ltu | tr--ev--use.location--ltu | EnumValue | ev |
| lux | tr--ev--use.location--lux | EnumValue | ev |
| lva | tr--ev--use.location--lva | EnumValue | ev |
| mco | tr--ev--use.location--mco | EnumValue | ev |
| mda | tr--ev--use.location--mda | EnumValue | ev |
| mkd | tr--ev--use.location--mkd | EnumValue | ev |
| mlt | tr--ev--use.location--mlt | EnumValue | ev |
| mne | tr--ev--use.location--mne | EnumValue | ev |
| nld | tr--ev--use.location--nld | EnumValue | ev |
| nnn | tr--ev--use.location--nnn | EnumValue | ev |
| nor | tr--ev--use.location--nor | EnumValue | ev |
| nzl | tr--ev--use.location--nzl | EnumValue | ev |
| phl | tr--ev--use.location--phl | EnumValue | ev |
| pol | tr--ev--use.location--pol | EnumValue | ev |
| prk | tr--ev--use.location--prk | EnumValue | ev |
| prt | tr--ev--use.location--prt | EnumValue | ev |
| rou | tr--ev--use.location--rou | EnumValue | ev |
| rus | tr--ev--use.location--rus | EnumValue | ev |
| sau | tr--ev--use.location--sau | EnumValue | ev |
| srb | tr--ev--use.location--srb | EnumValue | ev |
| svk | tr--ev--use.location--svk | EnumValue | ev |
| srr | tr--ev--use.location--srr | EnumValue | ev |
| svn | tr--ev--use.location--svn | EnumValue | ev |
| swe | tr--ev--use.location--swe | EnumValue | ev |
| tjk | tr--ev--use.location--tjk | EnumValue | ev |
| tur | tr--ev--use.location--tur | EnumValue | ev |
| twn | tr--ev--use.location--twn | EnumValue | ev |
| ukr | tr--ev--use.location--ukr | EnumValue | ev |
| undefined | tr--ev--use.location--undefined | EnumValue | ev |
| usa | tr--ev--use.location--usa | EnumValue | ev |
| vnm | tr--ev--use.location--vnm | EnumValue | ev |
| use.product-life-cycle | tr--dde--use.product-life-cycle | DatatypeDefinitionEnumeration | dde |
| design | tr--ev--use.product-life-cycle--design | EnumValue | ev |
| maintenance | tr--ev--use.product-life-cycle--maintenance | EnumValue | ev |
| realization | tr--ev--use.product-life-cycle--realization | EnumValue | ev |
| recycling | tr--ev--use.product-life-cycle--recycling | EnumValue | ev |
| undefined | tr--ev--use.product-life-cycle--undefined | EnumValue | ev |
| use phase | tr--ev--use.product-life-cycle--use-phase | EnumValue | ev |
| use.project-phase | tr--dde--use.project-phase | DatatypeDefinitionEnumeration | dde |
| close out | tr--ev--use.project-phase--close-out | EnumValue | ev |
| definition and planning | tr--ev--use.project-phase--definition-and-planning | EnumValue | ev |
| execution | tr--ev--use.project-phase--execution | EnumValue | ev |
| initiation | tr--ev--use.project-phase--initiation | EnumValue | ev |
| monitoring and control | tr--ev--use.project-phase--monitoring-and-control | EnumValue | ev |
| undefined | tr--ev--use.project-phase--undefined | EnumValue | ev |
| use.purpose | tr--dde--use.purpose | DatatypeDefinitionEnumeration | dde |
| availability | tr--ev--use.purpose--availability | EnumValue | ev |
| communication | tr--ev--use.purpose--communication | EnumValue | ev |
| future proof | tr--ev--use.purpose--future-proof | EnumValue | ev |
| health | tr--ev--use.purpose--health | EnumValue | ev |
| interoperability | tr--ev--use.purpose--interoperability | EnumValue | ev |
| maintainability | tr--ev--use.purpose--maintainability | EnumValue | ev |
| quality | tr--ev--use.purpose--quality | EnumValue | ev |
| relation | tr--ev--use.purpose--relation | EnumValue | ev |
| reliability | tr--ev--use.purpose--reliability | EnumValue | ev |
| safety | tr--ev--use.purpose--safety | EnumValue | ev |
| sustainablility | tr--ev--use.purpose--sustainablility | EnumValue | ev |
| undefined | tr--ev--use.purpose--undefined | EnumValue | ev |
| xhtml | tr--ddx--xhtml | DatatypeDefinitionXHTML | ddx |
- bib.al.original-language: en
- bib.dp.publication-date: 2025-03-01
- ids.document: 100000012
- ids.tracing: hash-F7EFC805557E3990B7FC1506618210D3D3CE057C8D5A6E45353C2B811C21E3FF
- obj.clause-number: Table 19
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### R181: Specification types (SpecTypes) (heading)
- bib.al.original-language: en
- bib.dp.publication-date: 2025-03-01
- ids.document: 100000012
- obj.clause-number: 8.4.2
- obj.element-name: heading
- obj.language: en
- obj.specobject-type: heading
- ChapterName: 8.4.2 Specification types (SpecTypes)

##### R182: Relation group types (RelationGroupTypes) (heading)
- bib.al.original-language: en
- bib.dp.publication-date: 2025-03-01
- ids.document: 100000012
- obj.clause-number: 8.4.2.1
- obj.element-name: heading
- obj.language: en
- obj.specobject-type: heading
- ChapterName: 8.4.2.1 Relation group types (RelationGroupTypes)

###### prov-100000012-3eeadbebd2d6466: Relation group types (RelationGroupTypes) (provision)
RelationGroupTypes see Table 20.
- bib.al.original-language: en
- bib.dp.publication-date: 2025-03-01
- ids.document: 100000012
- ids.tracing: hash-33579A7D28C8D22D8A5E20A98EDD6DEF44663780478D12C30E744CF4593A624A
- obj.clause-number: 8.4.2.1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-5108d8a6e2e849a

###### prov-100000012-5108d8a6e2e849a: RelationGroupTypes (provision)
Table 20 — RelationGroupTypes
| long name | identifier | class name | class name abbreviation |
| --- | --- | --- | --- |
| relation-group-standard | tr--rgt--relation-group-standard | RelationGroupType | rgt |
| relation-group-external | tr--rg--relation-group-standard--relation-group-external | RelationGroup | rg |
| relation-group-internal | tr--rg--relation-group-standard--relation-group-internal | RelationGroup | rg |
- bib.al.original-language: en
- bib.dp.publication-date: 2025-03-01
- ids.document: 100000012
- ids.tracing: hash-86510927989059F2C3A1725E4CFBF1FA568723A4FB97C5B08AD1DD1B3E16CFE9
- obj.clause-number: Table 20
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### R185: Specification types (SpecificationTypes) (heading)
- bib.al.original-language: en
- bib.dp.publication-date: 2025-03-01
- ids.document: 100000012
- obj.clause-number: 8.4.2.2
- obj.element-name: heading
- obj.language: en
- obj.specobject-type: heading
- ChapterName: 8.4.2.2 Specification types (SpecificationTypes)

###### prov-100000012-b274d186a12c4f9: Specification types (SpecificationTypes) (provision)
SpecificationTypes see Table 21.
- bib.al.original-language: en
- bib.dp.publication-date: 2025-03-01
- ids.document: 100000012
- ids.tracing: hash-EF986A69F38C948DA30D9491546FA389B7B43EBA2DCF16AC8BF6C7449A470391
- obj.clause-number: 8.4.2.2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-fec60e359d0a452

###### prov-100000012-fec60e359d0a452: SpecificationTypes (provision)
Table 21 — SpecificationTypes
| long name | identifier | class name | class name abbreviation |
| --- | --- | --- | --- |
| specification-standard | tr--st--specification-standard | SpecificationType | st |
| bib.al.original-language | tr--ads--specification-standard--bib.al.original-language | AttributeDefinitionString | ads |
| bib.as.amends | tr--ads--specification-standard--bib.as.amends | AttributeDefinitionString | ads |
| bib.az.amended-by | tr--ads--specification-standard--bib.az.amended-by | AttributeDefinitionString | ads |
| bib.ca.classification | tr--ads--specification-standard--bib.ca.classification | AttributeDefinitionString | ads |
| bib.ct.descriptors-german | tr--ads--specification-standard--bib.ct.descriptors-german | AttributeDefinitionString | ads |
| bib.di.document-identifier | tr--ads--specification-standard--bib.di.document-identifier | AttributeDefinitionString | ads |
| bib.dp.publication-date | tr--ads--specification-standard--bib.dp.publication-date | AttributeDefinitionString | ads |
| bib.et.descriptors-english | tr--ads--specification-standard--bib.et.descriptors-english | AttributeDefinitionString | ads |
| bib.ft.descriptors-french | tr--ads--specification-standard--bib.ft.descriptors-french | AttributeDefinitionString | ads |
| bib.ii.international-relationship | tr--ads--specification-standard--bib.ii.international-relationship | AttributeDefinitionString | ads |
| bib.rx.replaced-by | tr--ads--specification-standard--bib.rx.replaced-by | AttributeDefinitionString | ads |
| bib.rz.replaces | tr--ads--specification-standard--bib.rz.replaces | AttributeDefinitionString | ads |
| bib.tf.title-french | tr--adx--specification-standard--bib.tf.title-french | AttributeDefinitionXHTML | adx |
| bib.tg.title-german | tr--adx--specification-standard--bib.tg.title-german | AttributeDefinitionXHTML | adx |
| bib.ti.title-english | tr--adx--specification-standard--bib.ti.title-english | AttributeDefinitionXHTML | adx |
| bib.ts.document-type | tr--ads--specification-standard--bib.ts.document-type | AttributeDefinitionString | ads |
| bib.up.update-flag | tr--ads--specification-standard--bib.up.update-flag | AttributeDefinitionString | ads |
| obj.transformation-issues | tr--ads--specification-standard--obj.transformation-issues | AttributeDefinitionString | ads |
- bib.al.original-language: en
- bib.dp.publication-date: 2025-03-01
- ids.document: 100000012
- ids.tracing: hash-D77CE5A9C23AC00B312794D60D7B6B6D7FCAA8C5CC23F2D7760C8D65B57FD32B
- obj.clause-number: Table 21
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### R188: Specification object types (SpecObjectTypes) (heading)
- bib.al.original-language: en
- bib.dp.publication-date: 2025-03-01
- ids.document: 100000012
- obj.clause-number: 8.4.2.3
- obj.element-name: heading
- obj.language: en
- obj.specobject-type: heading
- ChapterName: 8.4.2.3 Specification object types (SpecObjectTypes)

###### prov-100000012-429fa64633ed46c: Specification object types (SpecObjectTypes) (provision)
SpecObjectTypes see Table 22.
- bib.al.original-language: en
- bib.dp.publication-date: 2025-03-01
- ids.document: 100000012
- ids.tracing: hash-C458A97CA79913C3E42B879AC81987DE1158784A79D41AFF8634EC8B3290A926
- obj.clause-number: 8.4.2.3
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-3b7380488c0646a

###### prov-100000012-3b7380488c0646a: SpecObjectTypes (provision)
Table 22 — SpecObjectTypes
| long name | identifier | class name | class name abbreviation |
| --- | --- | --- | --- |
| document | tr--sot--document | SpecObjectType | sot |
| bib.al.original-language | tr--ads--document--bib.al.original-language | AttributeDefinitionString | ads |
| bib.as.amends | tr--ads--document--bib.as.amends | AttributeDefinitionString | ads |
| bib.az.amended-by | tr--ads--document--bib.az.amended-by | AttributeDefinitionString | ads |
| bib.ca.classification | tr--ads--document--bib.ca.classification | AttributeDefinitionString | ads |
| bib.ct.descriptors-german | tr--ads--document--bib.ct.descriptors-german | AttributeDefinitionString | ads |
| bib.di.document-identifier | tr--ads--document--bib.di.document-identifier | AttributeDefinitionString | ads |
| bib.dp.publication-date | tr--ads--document--bib.dp.publication-date | AttributeDefinitionString | ads |
| bib.et.descriptors-english | tr--ads--document--bib.et.descriptors-english | AttributeDefinitionString | ads |
| bib.ft.descriptors-french | tr--ads--document--bib.ft.descriptors-french | AttributeDefinitionString | ads |
| bib.ii.international-relationship | tr--ads--document--bib.ii.international-relationship | AttributeDefinitionString | ads |
| bib.rx.replaced-by | tr--ads--document--bib.rx.replaced-by | AttributeDefinitionString | ads |
| bib.rz.replaces | tr--ads--document--bib.rz.replaces | AttributeDefinitionString | ads |
| bib.tf.title-french | tr--adx--document--bib.tf.title-french | AttributeDefinitionXHTML | adx |
| bib.tg.title-german | tr--adx--document--bib.tg.title-german | AttributeDefinitionXHTML | adx |
| bib.ti.title-english | tr--adx--document--bib.ti.title-english | AttributeDefinitionXHTML | adx |
| bib.ts.document-type | tr--ads--document--bib.ts.document-type | AttributeDefinitionString | ads |
| bib.up.update-flag | tr--ads--document--bib.up.update-flag | AttributeDefinitionString | ads |
| ids.document | tr--ads--document--ids.document | AttributeDefinitionString | ads |
| obj.language | tr--ade--document--obj.language | AttributeDefinitionEnumeration | ade |
| obj.specobject-type | tr--ade--document--obj.specobject-type | AttributeDefinitionEnumeration | ade |
| obj.transformation-issues | tr--ads--document--obj.transformation-issues | AttributeDefinitionString | ads |
| pub.harmonization | tr--ads--document--pub.harmonization | AttributeDefinitionString | ads |
| pub.originator | tr--ads--document--pub.originator | AttributeDefinitionString | ads |
| pub.software | tr--ads--document--pub.software | AttributeDefinitionString | ads |
| pub.supplier | tr--ads--document--pub.supplier | AttributeDefinitionString | ads |
| ReqIF.Text | tr--adx--document--reqif.text | AttributeDefinitionXHTML | adx |
| heading | tr--sot--heading | SpecObjectType | sot |
| bib.di.document-identifier | tr--ads--heading--bib.di.document-identifier | AttributeDefinitionString | ads |
| bib.dp.publication-date | tr--ads--heading--bib.dp.publication-date | AttributeDefinitionString | ads |
| ids.document | tr--ads--heading--ids.document | AttributeDefinitionString | ads |
| ids.element | tr--ads--heading--ids.element | AttributeDefinitionString | ads |
| ids.tracing | tr--ads--heading--ids.tracing | AttributeDefinitionString | ads |
| ids.unique | tr--ads--heading--ids.unique | AttributeDefinitionString | ads |
| obj.clause-heading | tr--ads--heading--obj.clause-heading | AttributeDefinitionString | ads |
| obj.clause-number | tr--ads--heading--obj.clause-number | AttributeDefinitionString | ads |
| obj.element-name | tr--ade--heading--obj.element-name | AttributeDefinitionEnumeration | ade |
| obj.language | tr--ade--heading--obj.language | AttributeDefinitionEnumeration | ade |
| obj.specobject-type | tr--ade--heading--obj.specobject-type | AttributeDefinitionEnumeration | ade |
| obj.transformation-issues | tr--ads--heading--obj.transformation-issues | AttributeDefinitionString | ads |
| ReqIF.ChapterName | tr--adx--heading--reqif.chaptername | AttributeDefinitionXHTML | adx |
| provision | tr--sot--provision | SpecObjectType | sot |
| bib.al.original-language | tr--ads--provision--bib.al.original-language | AttributeDefinitionString | ads |
| bib.as.amends | tr--ads--provision--bib.as.amends | AttributeDefinitionString | ads |
| bib.az.amended-by | tr--ads--provision--bib.az.amended-by | AttributeDefinitionString | ads |
| bib.ca.classification | tr--ads--provision--bib.ca.classification | AttributeDefinitionString | ads |
| bib.ct.descriptors-german | tr--ads--provision--bib.ct.descriptors-german | AttributeDefinitionString | ads |
| bib.di.document-identifier | tr--ads--provision--bib.di.document-identifier | AttributeDefinitionString | ads |
| bib.dp.publication-date | tr--ads--provision--bib.dp.publication-date | AttributeDefinitionString | ads |
| bib.et.descriptors-english | tr--ads--provision--bib.et.descriptors-english | AttributeDefinitionString | ads |
| bib.ft.descriptors-french | tr--ads--provision--bib.ft.descriptors-french | AttributeDefinitionString | ads |
| bib.ii.international-relationship | tr--ads--provision--bib.ii.international-relationship | AttributeDefinitionString | ads |
| bib.rx.replaced-by | tr--ads--provision--bib.rx.replaced-by | AttributeDefinitionString | ads |
| bib.rz.replaces | tr--ads--provision--bib.rz.replaces | AttributeDefinitionString | ads |
| bib.tf.title-french | tr--adx--provision--bib.tf.title-french | AttributeDefinitionXHTML | adx |
| bib.tg.title-german | tr--adx--provision--bib.tg.title-german | AttributeDefinitionXHTML | adx |
| bib.ti.title-english | tr--adx--provision--bib.ti.title-english | AttributeDefinitionXHTML | adx |
| bib.ts.document-type | tr--ads--provision--bib.ts.document-type | AttributeDefinitionString | ads |
| bib.up.update-flag | tr--ads--provision--bib.up.update-flag | AttributeDefinitionString | ads |
| ids.document | tr--ads--provision--ids.document | AttributeDefinitionString | ads |
| ids.element | tr--ads--provision--ids.element | AttributeDefinitionString | ads |
| ids.tracing | tr--ads--provision--ids.tracing | AttributeDefinitionString | ads |
| ids.unique | tr--ads--provision--ids.unique | AttributeDefinitionString | ads |
| ids.xpath-end | tr--ads--provision--ids.xpath-end | AttributeDefinitionString | ads |
| ids.xpath-start | tr--ads--provision--ids.xpath-start | AttributeDefinitionString | ads |
| obj.clause-heading | tr--ads--provision--obj.clause-heading | AttributeDefinitionString | ads |
| obj.clause-number | tr--ads--provision--obj.clause-number | AttributeDefinitionString | ads |
| obj.conversion-reliability | tr--adi--provision--obj.conversion-reliability | AttributeDefinitionInteger | adi |
| obj.element-name | tr--ade--provision--obj.element-name | AttributeDefinitionEnumeration | ade |
| obj.language | tr--ade--provision--obj.language | AttributeDefinitionEnumeration | ade |
| obj.modality | tr--ade--provision--obj.modality | AttributeDefinitionEnumeration | ade |
| obj.normativity | tr--ade--provision--obj.normativity | AttributeDefinitionEnumeration | ade |
| obj.specobject-type | tr--ade--provision--obj.specobject-type | AttributeDefinitionEnumeration | ade |
| obj.transformation-issues | tr--ads--provision--obj.transformation-issues | AttributeDefinitionString | ads |
| ReqIF.Text | tr--adx--provision--reqif.text | AttributeDefinitionXHTML | adx |
| use.business-process | tr--ade--provision--use.business-process | AttributeDefinitionEnumeration | ade |
| use.business-sector | tr--ade--provision--use.business-sector | AttributeDefinitionEnumeration | ade |
| use.date-usage-begins | tr--ads--provision--use.date-usage-begins | AttributeDefinitionString | ads |
| use.date-usage-ends | tr--ads--provision--use.date-usage-ends | AttributeDefinitionString | ads |
| use.interaction | tr--ade--provision--use.interaction | AttributeDefinitionEnumeration | ade |
| use.location | tr--ade--provision--use.location | AttributeDefinitionEnumeration | ade |
| use.product-category | tr--ads--provision--use.product-category | AttributeDefinitionString | ads |
| use.product-life-cycle | tr--ade--provision--use.product-life-cycle | AttributeDefinitionEnumeration | ade |
| use.project-phase | tr--ade--provision--use.project-phase | AttributeDefinitionEnumeration | ade |
| use.purpose | tr--ade--provision--use.purpose | AttributeDefinitionEnumeration | ade |
- bib.al.original-language: en
- bib.dp.publication-date: 2025-03-01
- ids.document: 100000012
- ids.tracing: hash-6462F09C034A3AECDC40E2F96F8017C9AC13FED5CE122AEF339F2D1AFE6B04E3
- obj.clause-number: Table 22
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### R191: Specification relation types (SpecRelationTypes) (heading)
- bib.al.original-language: en
- bib.dp.publication-date: 2025-03-01
- ids.document: 100000012
- obj.clause-number: 8.4.2.4
- obj.element-name: heading
- obj.language: en
- obj.specobject-type: heading
- ChapterName: 8.4.2.4 Specification relation types (SpecRelationTypes)

###### prov-100000012-c133237f6ee940f: Specification relation types (SpecRelationTypes) (provision)
SpecRelationTypes see Table 23.
- bib.al.original-language: en
- bib.dp.publication-date: 2025-03-01
- ids.document: 100000012
- ids.tracing: hash-907757C38E7CA560A886C4599A24EBFEB58921ED6EF16DF784B0D2B7EF16BCD5
- obj.clause-number: 8.4.2.4
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-d61b95fb57234b1

###### prov-100000012-d61b95fb57234b1: SpecRelationTypes (provision)
Table 23 — SpecRelationTypes
| long name | identifier | class name | class name abbreviation |
| --- | --- | --- | --- |
| cross-reference | tr--srt--cross-reference | SpecRelationTypes | srt |
- bib.al.original-language: en
- bib.dp.publication-date: 2025-03-01
- ids.document: 100000012
- ids.tracing: hash-8BC48A6CBF9C4458D7F6D38E4F742A7BE79AEB655C9A4C1F0E3797AE39F205C9
- obj.clause-number: Table 23
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### R194: Specifications (heading)
- bib.al.original-language: en
- bib.dp.publication-date: 2025-03-01
- ids.document: 100000012
- obj.clause-number: 8.4.3
- obj.element-name: heading
- obj.language: en
- obj.specobject-type: heading
- ChapterName: 8.4.3 Specifications

##### prov-100000012-83a8799aa7594e1: Specifications (provision)
The Specifications contain linkage to the SpecObject content elements.
- bib.al.original-language: en
- bib.dp.publication-date: 2025-03-01
- ids.document: 100000012
- ids.tracing: hash-17E3B6D4388DD7CB7E3DEF6F4EFAA8CED74B86385105623FF5B189EDE35077C8
- obj.clause-number: 8.4.3
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### R196: Specifications Objects (SpecObjects) (heading)
- bib.al.original-language: en
- bib.dp.publication-date: 2025-03-01
- ids.document: 100000012
- obj.clause-number: 8.4.4
- obj.element-name: heading
- obj.language: en
- obj.specobject-type: heading
- ChapterName: 8.4.4 Specifications Objects (SpecObjects)

##### prov-100000012-f7849602172e42c: Specifications Objects (SpecObjects) (provision)
The SpecObjects contain the unsorted collection of all content objects of the document.
- bib.al.original-language: en
- bib.dp.publication-date: 2025-03-01
- ids.document: 100000012
- ids.tracing: hash-BC4A85AC8F3430ECDE3A190231975BFF73597DC9DE8665234B01B5415A757027
- obj.clause-number: 8.4.4
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### R198: Specification relations (SpecRelations) (heading)
- bib.al.original-language: en
- bib.dp.publication-date: 2025-03-01
- ids.document: 100000012
- obj.clause-number: 8.4.5
- obj.element-name: heading
- obj.language: en
- obj.specobject-type: heading
- ChapterName: 8.4.5 Specification relations (SpecRelations)

##### prov-100000012-5e0db6380aa74dc: Specification relations (SpecRelations) (provision)
The SpecRelations contain a collection of all relations between the SpecObjects.
- bib.al.original-language: en
- bib.dp.publication-date: 2025-03-01
- ids.document: 100000012
- ids.tracing: hash-B7A6F19AA71B61A71BB7FB67E3D290D00BC06D90892CFB2D01F006B52F96E857
- obj.clause-number: 8.4.5
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### R200: Specification relation groups (SpecRelationGroups) (heading)
- bib.al.original-language: en
- bib.dp.publication-date: 2025-03-01
- ids.document: 100000012
- obj.clause-number: 8.4.6
- obj.element-name: heading
- obj.language: en
- obj.specobject-type: heading
- ChapterName: 8.4.6 Specification relation groups (SpecRelationGroups)

##### prov-100000012-30be391779fb4c3: Specification relation groups (SpecRelationGroups) (provision)
The SpecRelationGroups of the type “relation-group-standard” contains:
- a) “relation-group-internal”, where all internal relations of the document can be collected;
- b) “relation-group-external”, where all relations to other documents can be collected (all other standards are also represented by SpecObjects of the type “document”).
- bib.al.original-language: en
- bib.dp.publication-date: 2025-03-01
- ids.document: 100000012
- ids.tracing: hash-7A0D4F3E648F85709E27B4464D444746778043EF2E67CC7FB4A54930AC1A301F
- obj.clause-number: 8.4.6
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### R202: Class name abbreviations (in long names and identifiers) (heading)
- bib.al.original-language: en
- bib.dp.publication-date: 2025-03-01
- ids.document: 100000012
- obj.clause-number: 8.5
- obj.element-name: heading
- obj.language: en
- obj.specobject-type: heading
- ChapterName: 8.5 Class name abbreviations (in long names and identifiers)

#### prov-100000012-4972bb51403c4ad: Class name abbreviations (in long names and identifiers) (provision)
Class name abbreviations see Table 24.
- bib.al.original-language: en
- bib.dp.publication-date: 2025-03-01
- ids.document: 100000012
- ids.tracing: hash-01356DB4A53382978BAEF3AC9DCD41F3904AA665ECD60B34DCE74489566E87EC
- obj.clause-number: 8.5
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-01447481942145d

#### prov-100000012-01447481942145d: Class name abbreviations (provision)
Table 24 — Class name abbreviations
| abbreviation | class name |
| --- | --- |
| ade | AttributeDefinitionEnumeration |
| ads | AttributeDefinitionString |
| adx | AttributeDefinitionXHTML |
| ddd | DatatypeDefinitionDate |
| dde | DatatypeDefinitionEnumeration |
| ddi | DatatypeDefinitionInteger |
| dd | DatatypeDefinitions |
| dds | DatatypeDefinitionString |
| ddx | DatatypeDefinitionXHTML |
| ev | EnumValue |
| rgt | RelationGroupTypes |
| st | SpecificationTypes |
| sot | SpecObjectTypes |
| srt | SpecRelationTypes |
| tr | harmonized prefix “tr” for “technical rule” |
- bib.al.original-language: en
- bib.dp.publication-date: 2025-03-01
- ids.document: 100000012
- ids.tracing: hash-5250137EAC20CD5B03590D96BB950CD068C133CCC11448C1301CE7D83F339489
- obj.clause-number: Table 24
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

## R205: Semantic interoperability (heading)
- bib.al.original-language: en
- bib.dp.publication-date: 2025-03-01
- ids.document: 100000012
- obj.clause-number: 9
- obj.element-name: heading
- obj.language: en
- obj.specobject-type: heading
- ChapterName: 9 Semantic interoperability

### R206: Attribute conventions (heading)
- bib.al.original-language: en
- bib.dp.publication-date: 2025-03-01
- ids.document: 100000012
- obj.clause-number: 9.1
- obj.element-name: heading
- obj.language: en
- obj.specobject-type: heading
- ChapterName: 9.1 Attribute conventions

#### R207: Data field term; data field designation (heading)
- bib.al.original-language: en
- bib.dp.publication-date: 2025-03-01
- ids.document: 100000012
- obj.clause-number: 9.1.1
- obj.element-name: heading
- obj.language: en
- obj.specobject-type: heading
- ChapterName: 9.1.1 Data field term; data field designation

##### prov-100000012-5bb14f16d17a42d: Data field term; data field designation (provision)
Data field terms (see 8.2) shall represent the standardized data field designations in the user’s natural language.
- bib.al.original-language: en
- bib.dp.publication-date: 2025-03-01
- ids.document: 100000012
- ids.tracing: hash-15F4B5621B7ECA9B84FCB7206EDC0706BD2F3B17141FEF08025DCD00B24F4811
- obj.clause-number: 9.1.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R119

##### prov-100000012-fc8047a068d6411: Data field term; data field designation (provision)
Data field terms (see 8.2) shall be specified in English language to improve international operability.
- bib.al.original-language: en
- bib.dp.publication-date: 2025-03-01
- ids.document: 100000012
- ids.tracing: hash-AEE30D7A778C0204A9D375C78E2F9E616CB444C6A1FEAA98DD2D5AC9BB901AC4
- obj.clause-number: 9.1.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R119

##### prov-100000012-cdc77d40da7544d: Data field term; data field designation (provision)
For the documentation, the data field terms (see 8.2):
- shall be specified in English, French and German to support at least the languages most commonly used for public standards;
- should be documented in other languages as appropriate for the relevant stakeholders.
- bib.al.original-language: en
- bib.dp.publication-date: 2025-03-01
- ids.document: 100000012
- ids.tracing: hash-489E66B3EFF6B35544679FBE0D516C70B4C9A2BA9A8775C8BDD5C31A194EA5F6
- obj.clause-number: 9.1.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R119

#### R211: ReqIF™ attribute name (heading)
- bib.al.original-language: en
- bib.dp.publication-date: 2025-03-01
- ids.document: 100000012
- obj.clause-number: 9.1.2
- obj.element-name: heading
- obj.language: en
- obj.specobject-type: heading
- ChapterName: 9.1.2 ReqIF™ attribute name

##### prov-100000012-9e364ae94457468: ReqIF™ attribute name (provision)
Attribute names (see 8.2) shall be specified in English language to improve international operability.
- bib.al.original-language: en
- bib.dp.publication-date: 2025-03-01
- ids.document: 100000012
- ids.tracing: hash-55C6BCAA71E03BBD4BA3B6B5CCA972B04F32D808B69AD8B4109BC811AF300DC7
- obj.clause-number: 9.1.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R119

##### prov-100000012-9da77d6326a24ef: ReqIF™ attribute name (provision)
Attribute names (see 8.2) shall only contain the characters dash, the digits 0 to 9 and the lower-case letters a to z [.\-0123456789a-z], except the adopted attributes ReqIF.ChapterName (9.6.1) and ReqIF.Text (9.6.2).
- bib.al.original-language: en
- bib.dp.publication-date: 2025-03-01
- ids.document: 100000012
- ids.tracing: hash-78C17E89149CF933686A76A8FBDB634DD813CF5E15A408720A50C11D6E57C83F
- obj.clause-number: 9.1.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R119
- cross-reference -> R387
- cross-reference -> R393

##### prov-100000012-dc18d5f0c48640a: ReqIF™ attribute name (provision)
The attribute names ReqIF.ChapterName (9.6.1) and ReqIF.Text (9.6.2) shall accord with the prostep ReqIF™ 1.2 guideline to ensure compatibility with as many target software as possible.
- bib.al.original-language: en
- bib.dp.publication-date: 2025-03-01
- ids.document: 100000012
- ids.tracing: hash-E5C15830962A20D9900131664BCC88C975B2804C7F71C6B8D6A862B9383B329F
- obj.clause-number: 9.1.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R387
- cross-reference -> R393

#### R215: ReqIF™ data type (heading)
- bib.al.original-language: en
- bib.dp.publication-date: 2025-03-01
- ids.document: 100000012
- obj.clause-number: 9.1.3
- obj.element-name: heading
- obj.language: en
- obj.specobject-type: heading
- ChapterName: 9.1.3 ReqIF™ data type

##### prov-100000012-1eb879f0ddb247a: ReqIF™ data type (provision)
The ReqIF™ data type (see 8.2) shall be defined as:
- integer: if whole numbers may be applied only;
- value list (EnumValue): if users may select from fixed values only, so that the users can align values in the target systems easily;
- string: if users are allowed to change the values or values are not fixed;
- XHTML: if presentational markup according to XHTML™ 1.0 is required for an unambiguous interpretation of the value content.
- bib.al.original-language: en
- bib.dp.publication-date: 2025-03-01
- ids.document: 100000012
- ids.tracing: hash-52FABD52201E3D9C586A33268E7D121313554708903064A0E3871A0DA8FBA40D
- obj.clause-number: 9.1.3
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R119

##### prov-100000012-881af6010f344e9: ReqIF™ data type (provision)
To maintain strings interoperable:
- attribute list values should only contain the characters space, period, dash, the digits 0 to 9 and the lower-case letters a to z [ .\-0123456789a-z].
- attribute string values or XHTML™ 1.0 content shall only contain UTF-8 characters required for the text in the respective language.
- bib.al.original-language: en
- bib.dp.publication-date: 2025-03-01
- ids.document: 100000012
- ids.tracing: hash-21D51B6E67C7DD2DAF6F97DA3DC8DA865553687EF2B64E1E3D2882F189607423
- obj.clause-number: 9.1.3
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-830e93b06e0d419: ReqIF™ data type (provision)
The attribute values ReqIF.ChapterName (9.6.1) and ReqIF.Text (9.6.2) shall accord with the prostep ReqIF™ 1.2 guideline to ensure compatibility with as many target software as possible.
- bib.al.original-language: en
- bib.dp.publication-date: 2025-03-01
- ids.document: 100000012
- ids.tracing: hash-598854E843ABE6C4A86F01DB19E5030B6FBB679A14048B9B61B2DA87BED7967F
- obj.clause-number: 9.1.3
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R387
- cross-reference -> R393

##### prov-100000012-0b634d7099a547d: ReqIF™ data type (provision)
For value lists such the regions (see 8.3), the suppliers may update values to the state of the art if all stakeholders relevant for the interoperability context agree on the update.
- bib.al.original-language: en
- bib.dp.publication-date: 2025-03-01
- ids.document: 100000012
- ids.tracing: hash-6C4816B42C8E8BAFE8A8881995CAF366CA3EFF59682AE747F93184DFFDC1187F
- obj.clause-number: 9.1.3
- obj.element-name: paragraph
- obj.language: en
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R140

#### R220: ReqIF™ attribute value (heading)
- bib.al.original-language: en
- bib.dp.publication-date: 2025-03-01
- ids.document: 100000012
- obj.clause-number: 9.1.4
- obj.element-name: heading
- obj.language: en
- obj.specobject-type: heading
- ChapterName: 9.1.4 ReqIF™ attribute value

##### prov-100000012-e76479d4dbb047d: ReqIF™ attribute value (provision)
If language-dependent information is concerned, all ReqIF™ attribute values (see 8.2 and 8.3) shall be specified in English language to improve international operability.
- bib.al.original-language: en
- bib.dp.publication-date: 2025-03-01
- ids.document: 100000012
- ids.tracing: hash-0410EB8EFC31AFFC67BF0199456B00988C3C9946BF7A3CA76434269240FB0B37
- obj.clause-number: 9.1.4
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R119
- cross-reference -> R140

#### R222: Default value for attributes (heading)
- bib.al.original-language: en
- bib.dp.publication-date: 2025-03-01
- ids.document: 100000012
- obj.clause-number: 9.1.5
- obj.element-name: heading
- obj.language: en
- obj.specobject-type: heading
- ChapterName: 9.1.5 Default value for attributes

##### prov-100000012-a92b942f5b124d5: Default value for attributes (provision)
For all attributes that are required due to the schema or semantical specification, the attribute values (see 8.2) shall be set if no unambiguous default interpretation can be implied by the target software.
- bib.al.original-language: en
- bib.dp.publication-date: 2025-03-01
- ids.document: 100000012
- ids.tracing: hash-B337979746E1D7546FFDDF9DA8359EEB1D013B241290B036216BACA4FE2FC7C8
- obj.clause-number: 9.1.5
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R119

##### prov-100000012-888db24262614ba: Default value for attributes (provision)
All attribute value lists (see 8.3) shall contain “undefined” as value, so that this value can be set if a value is required but no other semantical default value can be applied.
- bib.al.original-language: en
- bib.dp.publication-date: 2025-03-01
- ids.document: 100000012
- ids.tracing: hash-E00852631AA49E4BD8F5A27C90C1C6C04E08E7CB43E3923BBF448C08A0BFE6AD
- obj.clause-number: 9.1.5
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R140

#### R225: Definition for attribute names and attribute values (heading)
- bib.al.original-language: en
- bib.dp.publication-date: 2025-03-01
- ids.document: 100000012
- obj.clause-number: 9.1.6
- obj.element-name: heading
- obj.language: en
- obj.specobject-type: heading
- ChapterName: 9.1.6 Definition for attribute names and attribute values

##### prov-100000012-de73883f94e2418: Definition for attribute names and attribute values (provision)
Definitions for attribute names (see 8.2) and for attribute values (see 8.3) shall be specified in English language to improve international operability.
- bib.al.original-language: en
- bib.dp.publication-date: 2025-03-01
- ids.document: 100000012
- ids.tracing: hash-668717509C71EDDAC6D79A51152521FED2EB8D5C2E8C7D887376C5E746DBD384
- obj.clause-number: 9.1.6
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R119
- cross-reference -> R140

##### prov-100000012-446aaf0aa7ce470: Definition for attribute names and attribute values (provision)
All definitions shall be so unambiguous that different users can achieve the same interpretation to ensure the best possible interoperability between different stakeholders.
- bib.al.original-language: en
- bib.dp.publication-date: 2025-03-01
- ids.document: 100000012
- ids.tracing: hash-8E4A041C8C971973165D6427467BE48BC7397A9E912EA8E97007D4EA01A8F87D
- obj.clause-number: 9.1.6
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### R228: Overflow of attribute values (heading)
- bib.al.original-language: en
- bib.dp.publication-date: 2025-03-01
- ids.document: 100000012
- obj.clause-number: 9.1.7
- obj.element-name: heading
- obj.language: en
- obj.specobject-type: heading
- ChapterName: 9.1.7 Overflow of attribute values

##### prov-100000012-fa106beb0a084a4: Overflow of attribute values (provision)
If the original content in the public standard exceeds a defined string length, the text of the content shall be truncated and finished with three periods for the ellipsis (“…”) to fit into the available string length.
- bib.al.original-language: en
- bib.dp.publication-date: 2025-03-01
- ids.document: 100000012
- ids.tracing: hash-19BB73CFA3CC107EEEF57EB146A8E39AE996F0BB0DE8A0E603A264246328C620
- obj.clause-number: 9.1.7
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-f336b8b102d64a8: Overflow of attribute values (provision)
EXAMPLE:
Heading as UTF-8 string limited to a value below the 1024 bytes specified for headings:
“Xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx …”
- bib.al.original-language: en
- bib.dp.publication-date: 2025-03-01
- ids.document: 100000012
- ids.tracing: hash-D0EE8142F400A61C53B5A98A4328B60C54360A9E23126B886E5250E4BE57C2FF
- obj.clause-number: 9.1.7
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-ac2e89fc60574fd: Overflow of attribute values (provision)
Heading as UTF-8 string limited to a value below the 1024 bytes specified for headings:
“Xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx Xxxxx xxxxx Xxxxxxx xxx …”
- bib.al.original-language: en
- bib.dp.publication-date: 2025-03-01
- ids.document: 100000012
- ids.tracing: hash-24C9F4DEAF360A032F2B09E02031FC420A5A8457BB80CC8E851B77E06906473A
- obj.clause-number: 9.1.7
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-e0b834937be84e7: Overflow of attribute values (provision)
If an attribute value is reduced to fit into the specified value limits, the supplier should provide an error report so that the users can validate the impact of the limitation.
- bib.al.original-language: en
- bib.dp.publication-date: 2025-03-01
- ids.document: 100000012
- ids.tracing: hash-A72BFE2D873230052257EAF680EB8467D7468DCE8519155AF97500879683E335
- obj.clause-number: 9.1.7
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

#### R233: Localization of attributes (heading)
- bib.al.original-language: en
- bib.dp.publication-date: 2025-03-01
- ids.document: 100000012
- obj.clause-number: 9.1.8
- obj.element-name: heading
- obj.language: en
- obj.specobject-type: heading
- ChapterName: 9.1.8 Localization of attributes

##### prov-100000012-2b8740fe3021417: Localization of attributes (provision)
The supplier shall locate the attributes according to 8.2.
- bib.al.original-language: en
- bib.dp.publication-date: 2025-03-01
- ids.document: 100000012
- ids.tracing: hash-F9B487EA39D884F7E4B6368811C7386F06BFA448F4A90D82DC8E75891FA9CE8B
- obj.clause-number: 9.1.8
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R119

##### prov-100000012-56cfb03db41240b: Localization of attributes (provision)
The supplier shall locate the bibliographic document metadata (see 8.2.1.4) for each SpecObject in the ReqIF™ file depending on the type of the SpecObject (see 8.2.1.2).
- bib.al.original-language: en
- bib.dp.publication-date: 2025-03-01
- ids.document: 100000012
- ids.tracing: hash-1540F546CE9CAD48426EDBF8F7D51600777FFD2D2CA6870FED2259755FB85934
- obj.clause-number: 9.1.8
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R130
- cross-reference -> R124

##### prov-100000012-bb71c537f5bb477: Localization of attributes (provision)
If the attribute obj.specobject-type (8.2.1.2) has the value (see 9.7.8):
- “document”, the supplier shall set the bibliographic document metadata according to 8.2.1.4 at the SpecObject with the title page metadata and at the specification of the ReqIF™ file.
- “heading”, the supplier shall set only the attributes bib.di.document-identifier (8.2.1.4) and bib.dp.publication-date (8.2.1.4) at the SpecObject with the heading of a provision.
- “provision”, the supplier shall set the bibliographic document metadata according to 8.2.1.4 at the SpecObject with the content of a provision itself.
- bib.al.original-language: en
- bib.dp.publication-date: 2025-03-01
- ids.document: 100000012
- ids.tracing: hash-A16B17C72D6DDFFC71AD9EDF361D095BA7142FC158C47E04824ED614E0D574DE
- obj.clause-number: 9.1.8
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124
- cross-reference -> R436
- cross-reference -> R130

### R237: Attribute or content outputs (heading)
- bib.al.original-language: en
- bib.dp.publication-date: 2025-03-01
- ids.document: 100000012
- obj.clause-number: 9.2
- obj.element-name: heading
- obj.language: en
- obj.specobject-type: heading
- ChapterName: 9.2 Attribute or content outputs

#### R238: Data field term or definition (ReqIF:DESC) (heading)
- bib.al.original-language: en
- bib.dp.publication-date: 2025-03-01
- ids.document: 100000012
- obj.clause-number: 9.2.1
- obj.element-name: heading
- obj.language: en
- obj.specobject-type: heading
- ChapterName: 9.2.1 Data field term or definition (ReqIF:DESC)

##### prov-100000012-85c8861c6f00471: Data field term or definition (ReqIF:DESC) (provision)
Either the data field term (see 8.2), the definition (see 8.2) or both information concatenated shall be output to the ReqIF™ file as value of the attribute DESC at the elements according to 11.3.
- bib.al.original-language: en
- bib.dp.publication-date: 2025-03-01
- ids.document: 100000012
- ids.tracing: hash-F1C9B89E1190D8BEA928938ABB87875CCFA76BCBE7953149481EEC6ED12D0737
- obj.clause-number: 9.2.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R119
- cross-reference -> R609

##### prov-100000012-4f0d067ba9ce4f6: Data field term or definition (ReqIF:DESC) (provision)
EXAMPLE 1:
The data field term (see 8.2) term is the value of the attribute DESC:
<ATTRIBUTE-DEFINITION-ENUMERATION DESC="Modality; bindingness" ...>
- bib.al.original-language: en
- bib.dp.publication-date: 2025-03-01
- ids.document: 100000012
- ids.tracing: hash-37D93750B9AA6610C25249D1AB99DC5B53179A29AFCD181F61F22A17DE869E93
- obj.clause-number: 9.2.1
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-d78175fd935948b: Data field term or definition (ReqIF:DESC) (provision)
The data field term (see 8.2) term is the value of the attribute DESC:
- bib.al.original-language: en
- bib.dp.publication-date: 2025-03-01
- ids.document: 100000012
- ids.tracing: hash-4E826261753A2A86FAAAAE2534B6E586F3297E6D405024CC90154EEFB912DF67
- obj.clause-number: 9.2.1
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> R119

##### prov-100000012-cbd62e1d321c49a: Data field term or definition (ReqIF:DESC) (provision)
EXAMPLE 2:
The definition (see 8.2) is the value of the attribute DESC:
<ATTRIBUTE-DEFINITION-ENUMERATION DESC="level of obligation for a governing provision in the standard model " IDENTIFIER="tr--ade--provision--obj.modality" ...>
- bib.al.original-language: en
- bib.dp.publication-date: 2025-03-01
- ids.document: 100000012
- ids.tracing: hash-A00D5D1A74B8D96BFB956A72042FFC72B682724959C57F64013A0A02263B9A75
- obj.clause-number: 9.2.1
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-654c9cd3f23e4b7: Data field term or definition (ReqIF:DESC) (provision)
The definition (see 8.2) is the value of the attribute DESC:
- bib.al.original-language: en
- bib.dp.publication-date: 2025-03-01
- ids.document: 100000012
- ids.tracing: hash-00FB6D678C07AFE995BC969931016715C295837A3297F0AF26E79FF027481151
- obj.clause-number: 9.2.1
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> R119

##### prov-100000012-e37d4ebc25ee40e: Data field term or definition (ReqIF:DESC) (provision)
EXAMPLE 3:
The data field term (see 8.2) and the definition (see 8.2) concatenated are the value of the attribute DESC:
<ATTRIBUTE-DEFINITION-ENUMERATION DESC="Modality; bindingness: level of obligation for a governing provision in the standard model " ...>
- bib.al.original-language: en
- bib.dp.publication-date: 2025-03-01
- ids.document: 100000012
- ids.tracing: hash-80C5254C544AC5E264488DE5A1C2BD5364785E82BC25B5AB5ADC09630EA630D7
- obj.clause-number: 9.2.1
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-40a7802a2b10461: Data field term or definition (ReqIF:DESC) (provision)
The data field term (see 8.2) and the definition (see 8.2) concatenated are the value of the attribute DESC:
- bib.al.original-language: en
- bib.dp.publication-date: 2025-03-01
- ids.document: 100000012
- ids.tracing: hash-6F74C2BA405CCA339AF8AE234320F25CD2B12964DDBF6D03AD86F2D00B7E0FA5
- obj.clause-number: 9.2.1
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> R119

#### R246: Identifier (ReqIF:IDENTIFIER) (heading)
- bib.al.original-language: en
- bib.dp.publication-date: 2025-03-01
- ids.document: 100000012
- obj.clause-number: 9.2.2
- obj.element-name: heading
- obj.language: en
- obj.specobject-type: heading
- ChapterName: 9.2.2 Identifier (ReqIF:IDENTIFIER)

##### prov-100000012-1f847f4f08f4423: Identifier (ReqIF:IDENTIFIER) (provision)
The identifier (see 8.2) shall be output to the ReqIF™ file as value of the attribute IDENTIFIER at the elements according to 11.3.
- bib.al.original-language: en
- bib.dp.publication-date: 2025-03-01
- ids.document: 100000012
- ids.tracing: hash-669BA88C7389C66D97A6937BF28993EC164510CB0501B6C4BCCF61B28BF65BD7
- obj.clause-number: 9.2.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R119
- cross-reference -> R609

##### prov-100000012-55d8af8b9bd341c: Identifier (ReqIF:IDENTIFIER) (provision)
EXAMPLE 1:
The identifier (see 8.3) term is the value of the attribute DESC:
<DATATYPE-DEFINITION-ENUMERATION IDENTIFIER="tr--dde--modality" LAST-CHANGE="..." LONG-NAME="modality"> <SPECIFIED-VALUES> ... <ENUM-VALUE IDENTIFIER="tr--ev--modality--requirement" LAST-CHANGE="..." LONG-NAME="requirement"> <PROPERTIES> <EMBEDDED-VALUE KEY="7" OTHER-CONTENT="requirement"/> </PROPERTIES> </ENUM-VALUE> ... </SPECIFIED-VALUES> </ DATATYPE-DEFINITION-ENUMERATION>
- bib.al.original-language: en
- bib.dp.publication-date: 2025-03-01
- ids.document: 100000012
- ids.tracing: hash-CBEDC13E2F46BEBBEF46D5B0234C500B4FE83576458F0579B0ED0164D668E588
- obj.clause-number: 9.2.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-5d6ce2e336d94d0: Identifier (ReqIF:IDENTIFIER) (provision)
The identifier (see 8.3) term is the value of the attribute DESC:
- bib.al.original-language: en
- bib.dp.publication-date: 2025-03-01
- ids.document: 100000012
- ids.tracing: hash-967EC66660EA00EED0A659D49F89C01FD0FF33B8F26CA10FAA0F7C2B874FE635
- obj.clause-number: 9.2.2
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> R140

##### prov-100000012-616f86b84d9848d: Identifier (ReqIF:IDENTIFIER) (provision)
The identifier (see 8.3) shall be output to the ReqIF™ file as content of the elements according to 11.3.
- bib.al.original-language: en
- bib.dp.publication-date: 2025-03-01
- ids.document: 100000012
- ids.tracing: hash-9368B2FED091A09DF8B6BEF5DCAAF8757B8EE4F0F3C4DE1AE4814392B7A37B9B
- obj.clause-number: 9.2.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R140
- cross-reference -> R609

##### prov-100000012-800018062538448: Identifier (ReqIF:IDENTIFIER) (provision)
EXAMPLE 2:
The identifier (see 8.3) is the content of exemplary elements:
<ATTRIBUTE-VALUE-ENUMERATION> <VALUES> <ENUM-VALUE-REF>tr--ev--modality--requirement</ENUM-VALUE-REF> </VALUES> <DEFINITION> <ATTRIBUTE-DEFINITION-ENUMERATION-REF>tr--ade--provision--obj.modality </ATTRIBUTE-DEFINITION-ENUMERATION-REF> </DEFINITION> </ATTRIBUTE-VALUE-ENUMERATION>
- bib.al.original-language: en
- bib.dp.publication-date: 2025-03-01
- ids.document: 100000012
- ids.tracing: hash-FC40F471355B7B8AEAAD347B419D624C6A4A36830505C01E9502FE1435C38F50
- obj.clause-number: 9.2.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-9d5d00e0d8b246c: Identifier (ReqIF:IDENTIFIER) (provision)
The identifier (see 8.3) is the content of exemplary elements:
- bib.al.original-language: en
- bib.dp.publication-date: 2025-03-01
- ids.document: 100000012
- ids.tracing: hash-5EEC0F83245708E4DE5FC9D37D321BD72EAE084BB3E1211F4BAE43802A2D1399
- obj.clause-number: 9.2.2
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> R140

##### prov-100000012-05b75167255c412: Identifier (ReqIF:IDENTIFIER) (provision)
The attribute identifiers shall be implemented according to 8.4, using the harmonized class name abbreviations for this application (see 8.5).
- bib.al.original-language: en
- bib.dp.publication-date: 2025-03-01
- ids.document: 100000012
- ids.tracing: hash-0918C98CF8DF6B3CFE87C2BDD035080821A6F5E37358F37FA0CA47282F74F361
- obj.clause-number: 9.2.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R177
- cross-reference -> R202

#### R254: ReqIF™ attribute name (ReqIF:LONG-NAME) (heading)
- bib.al.original-language: en
- bib.dp.publication-date: 2025-03-01
- ids.document: 100000012
- obj.clause-number: 9.2.3
- obj.element-name: heading
- obj.language: en
- obj.specobject-type: heading
- ChapterName: 9.2.3 ReqIF™ attribute name (ReqIF:LONG-NAME)

##### prov-100000012-79837664c77d4a2: ReqIF™ attribute name (ReqIF:LONG-NAME) (provision)
The attribute name (see 8.2) shall be output to the ReqIF™ file as value of the attribute LONG-NAME at the elements according to 11.3.
- bib.al.original-language: en
- bib.dp.publication-date: 2025-03-01
- ids.document: 100000012
- ids.tracing: hash-FE7A238A1FB855E58703C3CD2BBB61D9A083A46B5045548A94923029E91AE952
- obj.clause-number: 9.2.3
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R119
- cross-reference -> R609

##### prov-100000012-07ea585a61fa4b4: ReqIF™ attribute name (ReqIF:LONG-NAME) (provision)
EXAMPLE: <DATATYPE-DEFINITION-ENUMERATION IDENTIFIER="tr--dde--modality" LAST-CHANGE="..." LONG-NAME="modality">
- bib.al.original-language: en
- bib.dp.publication-date: 2025-03-01
- ids.document: 100000012
- ids.tracing: hash-8F22DAF4ECCED3665C74357F117FF7F61A7B953F37EDC4E35EA1B37EE564419A
- obj.clause-number: 9.2.3
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### R257: ReqIF™ attribute value (ReqIF:LONG-NAME) (heading)
- bib.al.original-language: en
- bib.dp.publication-date: 2025-03-01
- ids.document: 100000012
- obj.clause-number: 9.2.4
- obj.element-name: heading
- obj.language: en
- obj.specobject-type: heading
- ChapterName: 9.2.4 ReqIF™ attribute value (ReqIF:LONG-NAME)

##### prov-100000012-e9ad22addb624d4: ReqIF™ attribute value (ReqIF:LONG-NAME) (provision)
The attribute value (see 8.2) shall be output to the ReqIF™ file as value of the attribute LONG-NAME at the elements according to 11.3.
- bib.al.original-language: en
- bib.dp.publication-date: 2025-03-01
- ids.document: 100000012
- ids.tracing: hash-A9E280668464D4921E97215990A973A4BB805ED54FA8EC30915945A44A4A4642
- obj.clause-number: 9.2.4
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R119
- cross-reference -> R609

##### prov-100000012-695a88c347634f4: ReqIF™ attribute value (ReqIF:LONG-NAME) (provision)
EXAMPLE: <ENUM-VALUE IDENTIFIER="tr--ev--modality--requirement" LAST-CHANGE="..." LONG-NAME="requirement">
- bib.al.original-language: en
- bib.dp.publication-date: 2025-03-01
- ids.document: 100000012
- ids.tracing: hash-9586DC25C99EB2EF363FF9440DDC6C9C5E9B1122B3376161A4F7C93BD532665F
- obj.clause-number: 9.2.4
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### R260: Definition (ReqIF:DESC) (heading)
- bib.al.original-language: en
- bib.dp.publication-date: 2025-03-01
- ids.document: 100000012
- obj.clause-number: 9.2.5
- obj.element-name: heading
- obj.language: en
- obj.specobject-type: heading
- ChapterName: 9.2.5 Definition (ReqIF:DESC)

##### prov-100000012-de63e1df8a6b495: Definition (ReqIF:DESC) (provision)
For attribute values, the definition (see 8.3) shall be output to the ReqIF™ file as value of the attribute DESC at the elements according to 11.3.
- bib.al.original-language: en
- bib.dp.publication-date: 2025-03-01
- ids.document: 100000012
- ids.tracing: hash-8793D8A7BD2D977A8AA6F62CE288B780ACF108CA07D19A7C90622A014AC29139
- obj.clause-number: 9.2.5
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R140
- cross-reference -> R609

##### prov-100000012-a1083132155f4db: Definition (ReqIF:DESC) (provision)
EXAMPLE:
For DESC see 9.2.1 Example 2 or Example 3.
- bib.al.original-language: en
- bib.dp.publication-date: 2025-03-01
- ids.document: 100000012
- ids.tracing: hash-AB779C60C7A120E308E22CE780D22FF2F601833F13DDE08AFE30C7D7F8CC4E92
- obj.clause-number: 9.2.5
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-e4f70da20c454b1: Definition (ReqIF:DESC) (provision)
For DESC see 9.2.1 Example 2 or Example 3.
- bib.al.original-language: en
- bib.dp.publication-date: 2025-03-01
- ids.document: 100000012
- ids.tracing: hash-03D4C445F350A443EFD9A26BD21772633BCFA267D470BA650BB9BB343E10A260
- obj.clause-number: 9.2.5
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-100000012-cbd62e1d321c49a
- cross-reference -> prov-100000012-e37d4ebc25ee40e

#### R264: Is-editable (ReqIF:IS-EDITABLE) (heading)
- bib.al.original-language: en
- bib.dp.publication-date: 2025-03-01
- ids.document: 100000012
- obj.clause-number: 9.2.6
- obj.element-name: heading
- obj.language: en
- obj.specobject-type: heading
- ChapterName: 9.2.6 Is-editable (ReqIF:IS-EDITABLE)

##### prov-100000012-e12008798124450: Is-editable (ReqIF:IS-EDITABLE) (provision)
The attribute permissions (see 8.2) shall be output to the ReqIF™ file as value of the attribute IS-EDITABLE at the elements according to 11.3.
- bib.al.original-language: en
- bib.dp.publication-date: 2025-03-01
- ids.document: 100000012
- ids.tracing: hash-24DDFA4F1529D8E8FDF439D72D65D44B36D5A1BF0CF6FB9F50815159EB874A94
- obj.clause-number: 9.2.6
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R119
- cross-reference -> R609

##### prov-100000012-13b5351ed73044f: Is-editable (ReqIF:IS-EDITABLE) (provision)
Conflicting values for the attribute IS-EDITABLE should be resolved according to the prostep ReqIF™ 1.2 guideline.
- bib.al.original-language: en
- bib.dp.publication-date: 2025-03-01
- ids.document: 100000012
- ids.tracing: hash-4E82AEE158FAA391B49E0EC9BDAE1EB08A8D4163CF34313FCD627DF63A3FC2F8
- obj.clause-number: 9.2.6
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-54425a0648734e0: Is-editable (ReqIF:IS-EDITABLE) (provision)
EXAMPLE: <ATTRIBUTE-DEFINITION-ENUMERATION DESC="Modality; bindingness" IDENTIFIER="tr--ade--provision--obj.modality" IS-EDITABLE="true" LAST-CHANGE="..." LONG-NAME="obj.modality" MULTI-VALUED="false">
- bib.al.original-language: en
- bib.dp.publication-date: 2025-03-01
- ids.document: 100000012
- ids.tracing: hash-6AB2530DE638FA6D694FEE8AC14E8DD18DDF8D0CB4A0FEAAFC641AAEEB8A5948
- obj.clause-number: 9.2.6
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### R268: Last change (ReqIF:LAST-CHANGE) (heading)
- bib.al.original-language: en
- bib.dp.publication-date: 2025-03-01
- ids.document: 100000012
- obj.clause-number: 9.2.7
- obj.element-name: heading
- obj.language: en
- obj.specobject-type: heading
- ChapterName: 9.2.7 Last change (ReqIF:LAST-CHANGE)

##### prov-100000012-a2798e21ba20459: Last change (ReqIF:LAST-CHANGE) (provision)
According to the OMG ReqIF™ 1.2 specification, the attribute change information shall be output to the ReqIF™ file as value of the attribute LAST-CHANGE at the elements according to 11.3.
- bib.al.original-language: en
- bib.dp.publication-date: 2025-03-01
- ids.document: 100000012
- ids.tracing: hash-EE58E53C3D9E7305B3AB0F31D01499FD7C27F16FFF7CAB2990EB6783261668A0
- obj.clause-number: 9.2.7
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R609

##### prov-100000012-ea1855e21e70401: Last change (ReqIF:LAST-CHANGE) (provision)
Since the change information equals either the creation or the change of the element, it may only be used for managing changes for the same version of a document but not across different versions of the same document.
- bib.al.original-language: en
- bib.dp.publication-date: 2025-03-01
- ids.document: 100000012
- ids.tracing: hash-6D8316A5629C642F9DFE6CA7BC3E1DFD925EE890A0C48944DED2FB74EB1859DD
- obj.clause-number: 9.2.7
- obj.element-name: paragraph
- obj.language: en
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-be798e8cc4f1452: Last change (ReqIF:LAST-CHANGE) (provision)
To manage SpecObjects of the same fragment across all versions of the same document, the tracing ID (see 9.10.5) can be used if tracing IDs are provided by the supplier.
- bib.al.original-language: en
- bib.dp.publication-date: 2025-03-01
- ids.document: 100000012
- ids.tracing: hash-CEE740F3D674EBF97D7D892C2420D2A495D66F8850DE39C8777A6D34BCEF5E5E
- obj.clause-number: 9.2.7
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R513

#### R272: Maximum length (ReqIF:MAX-LENGTH) (heading)
- bib.al.original-language: en
- bib.dp.publication-date: 2025-03-01
- ids.document: 100000012
- obj.clause-number: 9.2.8
- obj.element-name: heading
- obj.language: en
- obj.specobject-type: heading
- ChapterName: 9.2.8 Maximum length (ReqIF:MAX-LENGTH)

##### prov-100000012-756e2440937641e: Maximum length (ReqIF:MAX-LENGTH) (provision)
For ReqIF™ data type string attributes, the maximum length (see 8.2) shall be output to the ReqIF™ file as value of the attribute MAX-LENGTH at the element <DATATYPE-DEFINITION-STRING>.
- bib.al.original-language: en
- bib.dp.publication-date: 2025-03-01
- ids.document: 100000012
- ids.tracing: hash-8D10B268A6D04D45CEFF890EE5F9FBBC2ED5A5F0F32AB14FFE285014E2D247C9
- obj.clause-number: 9.2.8
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R119

#### R274: Value list using multiple or single values (ReqIF:MULTI-VALUED) (heading)
- bib.al.original-language: en
- bib.dp.publication-date: 2025-03-01
- ids.document: 100000012
- obj.clause-number: 9.2.9
- obj.element-name: heading
- obj.language: en
- obj.specobject-type: heading
- ChapterName: 9.2.9 Value list using multiple or single values (ReqIF:MULTI-VALUED)

##### prov-100000012-ad7e01a719764b1: Value list using multiple or single values (ReqIF:MULTI-VALUED) (provision)
- If the ReqIF™ data type (see 8.2) is specified as “enum-multi”, the attribute MULTI-VALUED at the element <ATTRIBUTE-DEFINITION-ENUMERATION> shall be set to the value “true”.
- If the ReqIF™ data type (see 8.2) is specified as “enum-single”, the attribute MULTI-VALUED at the element <ATTRIBUTE-DEFINITION-ENUMERATION> shall be set to the value “false”.
- bib.al.original-language: en
- bib.dp.publication-date: 2025-03-01
- ids.document: 100000012
- ids.tracing: hash-3C4CD3ACF66149588A78FE0453CD3B704E950F87832AA5D10708C4076B1E293B
- obj.clause-number: 9.2.9
- obj.element-name: unordered-list
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-100000012-419fb42c27cd460: Value list using multiple or single values (ReqIF:MULTI-VALUED), list extract (provision)
| → | If the ReqIF™ data type (see 8.2) is specified as “enum-multi”, the attribute MULTI-VALUED at the element <ATTRIBUTE-DEFINITION-ENUMERATION> shall be set to the value “true”. |
| --- | --- |
- bib.al.original-language: en
- bib.dp.publication-date: 2025-03-01
- ids.document: 100000012
- ids.tracing: hash-224A865E1B35265A13894A1F720CCBD2D7084E20A3C09E9AA7EF47854EEE358A
- obj.clause-number: 9.2.9
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R119

###### prov-100000012-e7053c2d403a4d0: Value list using multiple or single values (ReqIF:MULTI-VALUED), list extract (provision)
| → | If the ReqIF™ data type (see 8.2) is specified as “enum-single”, the attribute MULTI-VALUED at the element <ATTRIBUTE-DEFINITION-ENUMERATION> shall be set to the value “false”. |
| --- | --- |
- bib.al.original-language: en
- bib.dp.publication-date: 2025-03-01
- ids.document: 100000012
- ids.tracing: hash-861787371836340F8D36072E5C17D518A8730DE1F6D82CE4496EDC59A7C3FCC5
- obj.clause-number: 9.2.9
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R119

#### R278: Other content (ReqIF:OTHER-CONTENT) (heading)
- bib.al.original-language: en
- bib.dp.publication-date: 2025-03-01
- ids.document: 100000012
- obj.clause-number: 9.2.10
- obj.element-name: heading
- obj.language: en
- obj.specobject-type: heading
- ChapterName: 9.2.10 Other content (ReqIF:OTHER-CONTENT)

##### prov-100000012-533f749c79cf49e: Other content (ReqIF:OTHER-CONTENT) (provision)
According to the OMG ReqIF™ 1.2 specification,
- the attribute name (see 8.2) should be output to ReqIF™ as value of the attribute OTHER-CONTENT at the element <EMBEDDED-VALUE/> (see Example).
- the counter from 1 to n should be output to ReqIF™ as value of the attribute KEY at the element <EMBEDDED-VALUE/> (see Example).
- bib.al.original-language: en
- bib.dp.publication-date: 2025-03-01
- ids.document: 100000012
- ids.tracing: hash-A77BBBB9DAB5745EF83710412F3CF0FB477E023DB1B5CB3687EDCA9A05CFC35F
- obj.clause-number: 9.2.10
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R119

##### prov-100000012-7ed199e9d63242b: Other content (ReqIF:OTHER-CONTENT) (provision)
EXAMPLE:
The value of the attribute LONG-NAME represented as value of the attributes KEY and OTHER-CONTENT at the element <EMBEDDED-VALUE>:
<DATATYPE-DEFINITION-ENUMERATION IDENTIFIER="tr--dde--modality" LAST-CHANGE="..." LONG-NAME="modality"> <SPECIFIED-VALUES> ... <ENUM-VALUE IDENTIFIER="tr--ev--modality--requirement" LAST-CHANGE="..." LONG-NAME="requirement"> <PROPERTIES> <EMBEDDED-VALUE KEY="7" OTHER-CONTENT="requirement"/> </PROPERTIES> </ENUM-VALUE> ... </SPECIFIED-VALUES> </DATATYPE-DEFINITION-ENUMERATION>
- bib.al.original-language: en
- bib.dp.publication-date: 2025-03-01
- ids.document: 100000012
- ids.tracing: hash-B48942ACD134C203E9A00DD6163CAD1E482C9225BD2C5A6E4E5AB3CAC0A1E3A2
- obj.clause-number: 9.2.10
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-e6dd9f1323144ef: Other content (ReqIF:OTHER-CONTENT) (provision)
The value of the attribute LONG-NAME represented as value of the attributes KEY and OTHER-CONTENT at the element <EMBEDDED-VALUE>:
- bib.al.original-language: en
- bib.dp.publication-date: 2025-03-01
- ids.document: 100000012
- ids.tracing: hash-08443A9235568EA30CB6B7BA398B23A2A02667F827788A788CBB8B09569DC453
- obj.clause-number: 9.2.10
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### R282: File format (heading)
- bib.al.original-language: en
- bib.dp.publication-date: 2025-03-01
- ids.document: 100000012
- obj.clause-number: 9.3
- obj.element-name: heading
- obj.language: en
- obj.specobject-type: heading
- ChapterName: 9.3 File format

#### R283: Form of the ReqIF™ file (heading)
- bib.al.original-language: en
- bib.dp.publication-date: 2025-03-01
- ids.document: 100000012
- obj.clause-number: 9.3.1
- obj.element-name: heading
- obj.language: en
- obj.specobject-type: heading
- ChapterName: 9.3.1 Form of the ReqIF™ file

##### prov-100000012-e3dc3a8b08eb4b5: Form of the ReqIF™ file (provision)
The ReqIF™ for a public standard shall be provided as zipped archive file.
- bib.al.original-language: en
- bib.dp.publication-date: 2025-03-01
- ids.document: 100000012
- ids.tracing: hash-99F7525FD1B1FA6AA2FDE456019915A7E6DCE3E07ECE59BBE8AB38815B043CA6
- obj.clause-number: 9.3.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-6b08572cb5e54ef: Form of the ReqIF™ file (provision)
The zipped archive file for a public standard shall use the usual file suffix “.reqifz”.
- bib.al.original-language: en
- bib.dp.publication-date: 2025-03-01
- ids.document: 100000012
- ids.tracing: hash-CE80C6E0D6623D11B4F2F8758504154D1BEFF8C958BE2086F6172919A6B3AFD4
- obj.clause-number: 9.3.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-8507e013a479442: Form of the ReqIF™ file (provision)
The zipped archive file for a public standard shall contain:
- the ReqIF™ file for one language variant of the public standard;
- all directories and files which are referenced as external entities from the ReqIF™ file.
- bib.al.original-language: en
- bib.dp.publication-date: 2025-03-01
- ids.document: 100000012
- ids.tracing: hash-ADDA9271061E4FA7C72271CCB66A3778D8D11F1857F8D5BD625AB9530083829D
- obj.clause-number: 9.3.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-ff5880c6b6c5412: Form of the ReqIF™ file (provision)
The ReqIF™ file shall use the usual file suffix “.reqif”.
- bib.al.original-language: en
- bib.dp.publication-date: 2025-03-01
- ids.document: 100000012
- ids.tracing: hash-76F2194D5154A4414F6548E8309C487B7759D2F75AFF83CE3FA3838CDFC17FFF
- obj.clause-number: 9.3.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-ab62ef58d3ad4d6: Form of the ReqIF™ file (provision)
To ensure interoperability, the ReqIF™ file shall contain only relative paths to the required external entities.
- bib.al.original-language: en
- bib.dp.publication-date: 2025-03-01
- ids.document: 100000012
- ids.tracing: hash-DB9402AD257B0CAF7A83BDD5DB1553F7A597F0C55B902220A90E5583EA93306B
- obj.clause-number: 9.3.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-d6e73ce0b76f4d7: Form of the ReqIF™ file (provision)
To provide multiple language variants for a public standard, the supplier shall supply a separate zipped archive file for each language variant with one ReqIF™ file and the referenced external entities.
- bib.al.original-language: en
- bib.dp.publication-date: 2025-03-01
- ids.document: 100000012
- ids.tracing: hash-55A4270229500B96E0B81CEBBEEB561D47D0E6B9496F2829559658712E2C6BA2
- obj.clause-number: 9.3.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### R290: Header of the ReqIF™ file (heading)
- bib.al.original-language: en
- bib.dp.publication-date: 2025-03-01
- ids.document: 100000012
- obj.clause-number: 9.3.2
- obj.element-name: heading
- obj.language: en
- obj.specobject-type: heading
- ChapterName: 9.3.2 Header of the ReqIF™ file

##### prov-100000012-6a45c7f4a5524f1: Header of the ReqIF™ file (provision)
For the ReqIF™ header, the document identifier (see 9.10.1) shall be output to the ReqIF™ file as value of the attribute IDENTIFIER at the element <REQ-IF-HEADER>.
- bib.al.original-language: en
- bib.dp.publication-date: 2025-03-01
- ids.document: 100000012
- ids.tracing: hash-298683098131C30232C82EDA45C45411749D3E65F2F4B1A1D40BCF1F44293218
- obj.clause-number: 9.3.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R492

##### prov-100000012-80466f0d65b249d: Header of the ReqIF™ file (provision)
For the ReqIF™ header, a date and time stamp for the creation shall be output to the ReqIF™ file as content at the element <CREATION-TIME>.
- bib.al.original-language: en
- bib.dp.publication-date: 2025-03-01
- ids.document: 100000012
- ids.tracing: hash-EC33CFB9BA2FDA1F91C8071FBB87B3E5AEC46D92A2D3066EEB62C2DC0427CD64
- obj.clause-number: 9.3.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-ada99be736d4481: Header of the ReqIF™ file (provision)
For the ReqIF™ header, the software (see 9.11.3) shall be output to the ReqIF™ file as content of the element:
- <COMMENT>;
- <REQ-IF-TOOL-ID>;
- <SOURCE-TOOL-ID>.
- bib.al.original-language: en
- bib.dp.publication-date: 2025-03-01
- ids.document: 100000012
- ids.tracing: hash-5F05F6F9620C5179B414C0C90AA31E77D0A266B2FA39F02614DFB6A3D6725881
- obj.clause-number: 9.3.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R535

##### prov-100000012-492195c2fa4e43e: Header of the ReqIF™ file (provision)
For the ReqIF™ header, ReqIF™ version shall be output to the ReqIF™ file as content of the element <REQ-IF-VERSION> (see Example).
- bib.al.original-language: en
- bib.dp.publication-date: 2025-03-01
- ids.document: 100000012
- ids.tracing: hash-C7CBEDB13B58DAF6EEA81110DC23B040A8DCC94562C17E7FD382FE7F7490C01C
- obj.clause-number: 9.3.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-43667fa9a5294bd: Header of the ReqIF™ file (provision)
For the ReqIF™ header, key information for a quick identification of the document (see 8.2.1.4) shall be output to the ReqIF™ file as content of the element <TITLE>.
- bib.al.original-language: en
- bib.dp.publication-date: 2025-03-01
- ids.document: 100000012
- ids.tracing: hash-9AE9498F46731981B7EFF883762F1C69D3CE9F1C3104655B59F2C1ED922DBA11
- obj.clause-number: 9.3.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R130

##### prov-100000012-64825c7503804a9: Header of the ReqIF™ file (provision)
EXAMPLE: <?xml version="1.0" encoding="UTF-8"?> <REQ-IF xmlns="http://www.omg.org/spec/ReqIF/20110401/reqif.xsd" xmlns:mml="http://www.w3.org/1998/Math/MathML" xmlns:xhtml="http://www.w3.org/1999/xhtml"> <THE-HEADER> <REQ-IF-HEADER IDENTIFIER="tr--e11d82e5--h"> <COMMENT>created by sts2reqif</COMMENT> <CREATION-TIME>2024-11-20T16:27:13.227+01:00</CREATION-TIME> <REQ-IF-TOOL-ID>sts2reqif 3.0.0</REQ-IF-TOOL-ID> <REQ-IF-VERSION>1.0</REQ-IF-VERSION> <SOURCE-TOOL-ID>sts2reqif</SOURCE-TOOL-ID> <TITLE>ISO 1463:1995-01, Metallic and oxide coatings – Measurement of ...</TITLE> </REQ-IF-HEADER> </THE-HEADER> ... </REQ-IF>
- bib.al.original-language: en
- bib.dp.publication-date: 2025-03-01
- ids.document: 100000012
- ids.tracing: hash-F2CED8BBD29D8E0D63036517B7BD8C3AF7276E64DF8AF0AE9CF11B29356089E3
- obj.clause-number: 9.3.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### R297: Tool extensions (heading)
- bib.al.original-language: en
- bib.dp.publication-date: 2025-03-01
- ids.document: 100000012
- obj.clause-number: 9.3.3
- obj.element-name: heading
- obj.language: en
- obj.specobject-type: heading
- ChapterName: 9.3.3 Tool extensions

##### prov-100000012-4708cc3879bd418: Tool extensions (provision)
The element <REQ-IF-TOOL-EXTENSION> is not used by this specification.
- bib.al.original-language: en
- bib.dp.publication-date: 2025-03-01
- ids.document: 100000012
- ids.tracing: hash-51708AAB13F7A1575606F3FE47FE9127DDB10E93BF7A587D5571D4F0DEA23989
- obj.clause-number: 9.3.3
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-1fc0d08b2077451: Tool extensions (provision)
The element <REQ-IF-TOOL-EXTENSION> may be used according to the prostep ReqIF™ 1.2 guideline if the interoperability between the relevant stakeholders is not jeopardized.
- bib.al.original-language: en
- bib.dp.publication-date: 2025-03-01
- ids.document: 100000012
- ids.tracing: hash-899AD5B5970A3C15924E8091B2E58D4B53D00A4A721041ACF450E3E59C408D6E
- obj.clause-number: 9.3.3
- obj.element-name: paragraph
- obj.language: en
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

### R300: Fragmentation of documents into provisions (SpecObjects) (heading)
- bib.al.original-language: en
- bib.dp.publication-date: 2025-03-01
- ids.document: 100000012
- obj.clause-number: 9.4
- obj.element-name: heading
- obj.language: en
- obj.specobject-type: heading
- ChapterName: 9.4 Fragmentation of documents into provisions (SpecObjects)

#### R301: Fragmentation options (heading)
- bib.al.original-language: en
- bib.dp.publication-date: 2025-03-01
- ids.document: 100000012
- obj.clause-number: 9.4.1
- obj.element-name: heading
- obj.language: en
- obj.specobject-type: heading
- ChapterName: 9.4.1 Fragmentation options

##### R302: Division-wise fragmentation (unused) (heading)
- bib.al.original-language: en
- bib.dp.publication-date: 2025-03-01
- ids.document: 100000012
- obj.clause-number: 9.4.1.1
- obj.element-name: heading
- obj.language: en
- obj.specobject-type: heading
- ChapterName: 9.4.1.1 Division-wise fragmentation (unused)

###### prov-100000012-0f6ecc51f45642a: Division-wise fragmentation (unused) (provision)
Each division such as a clause, subclause or annex is output as a SpecObject.
- bib.al.original-language: en
- bib.dp.publication-date: 2025-03-01
- ids.document: 100000012
- ids.tracing: hash-804D02B97D7DB889C4016E1A85D46F539A030B1821D51943FB66630ABB853498
- obj.clause-number: 9.4.1.1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### R304: Paragraph-wise fragmentation (unused) (heading)
- bib.al.original-language: en
- bib.dp.publication-date: 2025-03-01
- ids.document: 100000012
- obj.clause-number: 9.4.1.2
- obj.element-name: heading
- obj.language: en
- obj.specobject-type: heading
- ChapterName: 9.4.1.2 Paragraph-wise fragmentation (unused)

###### prov-100000012-52711b66ef114ef: Paragraph-wise fragmentation (unused) (provision)
Each paragraph and each paragraph-like block or display element such as enumeration items, notes, examples, ordering details, standard designations, warnings etc. is output as a SpecObject.
- bib.al.original-language: en
- bib.dp.publication-date: 2025-03-01
- ids.document: 100000012
- ids.tracing: hash-ADBDD78E7A2DDCC99333DD98E81B5E19E7FF221CAC388C8EC4F6473255E5A781
- obj.clause-number: 9.4.1.2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### R306: Sentence-wise fragmentation (harmonized standard method) (heading)
- bib.al.original-language: en
- bib.dp.publication-date: 2025-03-01
- ids.document: 100000012
- obj.clause-number: 9.4.1.3
- obj.element-name: heading
- obj.language: en
- obj.specobject-type: heading
- ChapterName: 9.4.1.3 Sentence-wise fragmentation (harmonized standard method)

###### prov-100000012-81e388624925407: Sentence-wise fragmentation (harmonized standard method) (provision)
The sentence-wise fragmentation shall be applied for public standards, except if all stakeholders relevant for the interoperability context agree on one of the alternative options (see 9.4.1.1 or 9.4.1.2).
- bib.al.original-language: en
- bib.dp.publication-date: 2025-03-01
- ids.document: 100000012
- ids.tracing: hash-DB6D2C4DC11C53B279F792872F85A93CE01AB89C74139639171E9BD7E01C8B2E
- obj.clause-number: 9.4.1.3
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R302
- cross-reference -> R304

#### R308: Sentence determination (heading)
- bib.al.original-language: en
- bib.dp.publication-date: 2025-03-01
- ids.document: 100000012
- obj.clause-number: 9.4.2
- obj.element-name: heading
- obj.language: en
- obj.specobject-type: heading
- ChapterName: 9.4.2 Sentence determination

##### prov-100000012-4daa9129633c4db: Sentence determination (provision)
- If the sentence is not the partial content of a so-called atomic element (see 9.4.3), each sentence shall be output as a SpecObject.
- If the sentence is the partial content of a so-called atomic element (see 9.4.3), the whole atomic element shall be output as one SpecObject.
- If the sentence would run out of a so-called terminating element (see 9.4.4), it shall be treated according to 9.4.4, since an expression may not run out of its logical context.
- bib.al.original-language: en
- bib.dp.publication-date: 2025-03-01
- ids.document: 100000012
- ids.tracing: hash-EC32CC63F83951FA49EEB365B5BD22741EC0DEFB994DD3E882D9C31828705EA1
- obj.clause-number: 9.4.2
- obj.element-name: unordered-list
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-100000012-242db23ec160404: Sentence determination, list extract (provision)
| → | If the sentence is not the partial content of a so-called atomic element (see 9.4.3), each sentence shall be output as a SpecObject. |
| --- | --- |
- bib.al.original-language: en
- bib.dp.publication-date: 2025-03-01
- ids.document: 100000012
- ids.tracing: hash-BE0CE90A08D64278FC643B9228480B0C6D305879B12BFE5D27C9808999A7FA93
- obj.clause-number: 9.4.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R334

###### prov-100000012-f862835f8f15423: Sentence determination, list extract (provision)
| → | If the sentence is the partial content of a so-called atomic element (see 9.4.3), the whole atomic element shall be output as one SpecObject. |
| --- | --- |
- bib.al.original-language: en
- bib.dp.publication-date: 2025-03-01
- ids.document: 100000012
- ids.tracing: hash-91F8448D2B70929D50751FB786DC89D00A75ACAC6CDE7BE85F679602F3114DAC
- obj.clause-number: 9.4.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R334

###### prov-100000012-9e1bc030e41c48a: Sentence determination, list extract (provision)
| → | If the sentence would run out of a so-called terminating element (see 9.4.4), it shall be treated according to 9.4.4, since an expression may not run out of its logical context. |
| --- | --- |
- bib.al.original-language: en
- bib.dp.publication-date: 2025-03-01
- ids.document: 100000012
- ids.tracing: hash-E980D8BA1CA8BF8533D34A1B7C0EE3819EB71888D198C2212922E88478CFB181
- obj.clause-number: 9.4.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R338

##### prov-100000012-1c2a9279977e48e: Sentence determination (provision)
EXAMPLE 1:
The Sentence begins in the paragraph and is ended in a list contained therein.
- bib.al.original-language: en
- bib.dp.publication-date: 2025-03-01
- ids.document: 100000012
- ids.tracing: hash-A6B6B065B6C80A48838B769C640FB34E858C8A6C963C899A3FC3B31B74144173
- obj.clause-number: 9.4.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-0bc6def481e14aa: Sentence determination (provision)
The Sentence begins in the paragraph and is ended in a list contained therein.
- bib.al.original-language: en
- bib.dp.publication-date: 2025-03-01
- ids.document: 100000012
- ids.tracing: hash-BBF7EFF96DDFA51A3C9C85BDA0F66AB6EDB04CBDFD35F7BDEE3EF849EB61468F
- obj.clause-number: 9.4.2
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-74caf813aacb4fc: Sentence determination (provision)
EXAMPLE 2:
The Sentence begins in the paragraph and is only ended in a following paragraphs or display elements contained therein.
- bib.al.original-language: en
- bib.dp.publication-date: 2025-03-01
- ids.document: 100000012
- ids.tracing: hash-98E4E1EC77AB202BA2D902A0913CEE018B16917DF06A0A20448A3316F31FEA9E
- obj.clause-number: 9.4.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-b08350f5b3f343e: Sentence determination (provision)
The Sentence begins in the paragraph and is only ended in a following paragraphs or display elements contained therein.
- bib.al.original-language: en
- bib.dp.publication-date: 2025-03-01
- ids.document: 100000012
- ids.tracing: hash-826A90EDAD2E07FFE9B189B380F62F1251B241C1B7D3058E4A191CA1D9C5736B
- obj.clause-number: 9.4.2
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-7a28039cbe7a4af: Sentence determination (provision)
EXAMPLE 3:
The Sentence begins in a table cell and is only ended in a succeeding table cell.
- bib.al.original-language: en
- bib.dp.publication-date: 2025-03-01
- ids.document: 100000012
- ids.tracing: hash-0D76E6B4889B6F7C54DE2D3F72204814DB07A2D514D6621BA1F5F233D20D13B9
- obj.clause-number: 9.4.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-c0d0047dfb97404: Sentence determination (provision)
The Sentence begins in a table cell and is only ended in a succeeding table cell.
- bib.al.original-language: en
- bib.dp.publication-date: 2025-03-01
- ids.document: 100000012
- ids.tracing: hash-9302DDEB8C866BA1BC2450237873F65A331A51F21DDD640721DA87E319836F67
- obj.clause-number: 9.4.2
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-1faeb89ce8b44fe: Sentence determination (provision)
If the sentence has been determined using natural language processing, sentences should:
- contain at least three words;
- not be terminated by common abbreviations finished by a period;
- not be terminated by a period which represents a decimal separator sign;
- not be finished by sentence signs which are part of a specific technical notation;
- be terminated by true sentence signs, only.
- bib.al.original-language: en
- bib.dp.publication-date: 2025-03-01
- ids.document: 100000012
- ids.tracing: hash-83286A46D9D2F86606475BBEA2063A0F945682304542088F760644EAF8E5DF2D
- obj.clause-number: 9.4.2
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-712e2fa7b2fa447: Sentence determination (provision)
EXAMPLE 4:
Not terminating abbreviation within the sentence:
“Apples, pears, plums etc. are all fruits”.
- bib.al.original-language: en
- bib.dp.publication-date: 2025-03-01
- ids.document: 100000012
- ids.tracing: hash-F2104A38C7F7189AA24C1327EBAFB3B4079BA8C8087A44549A0993411CF22AE1
- obj.clause-number: 9.4.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-3d306667634a44e: Sentence determination (provision)
Not terminating abbreviation within the sentence:
“Apples, pears, plums etc. are all fruits”.
- bib.al.original-language: en
- bib.dp.publication-date: 2025-03-01
- ids.document: 100000012
- ids.tracing: hash-33A41147B64991F6154662A9193B01A4D4C2DF3D251E270DD9083A50B4A06160
- obj.clause-number: 9.4.2
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-108533ab557b4f9: Sentence determination (provision)
EXAMPLE 5:
Terminating abbreviation at the end of the sentence.
“Fruits are apples, pears, plums, etc. Everything else are vegetables.”
- bib.al.original-language: en
- bib.dp.publication-date: 2025-03-01
- ids.document: 100000012
- ids.tracing: hash-59CCB309A59F753A5912107E7C3669ABF1F9F6E58DB818160017AEAFC0DB6C0B
- obj.clause-number: 9.4.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-76049880f0e2451: Sentence determination (provision)
Terminating abbreviation at the end of the sentence.
“Fruits are apples, pears, plums, etc. Everything else are vegetables.”
- bib.al.original-language: en
- bib.dp.publication-date: 2025-03-01
- ids.document: 100000012
- ids.tracing: hash-BC6A4615D01AE61049C6027D7A96EAD461C5692628266BA2D85CCE9680EF6CAB
- obj.clause-number: 9.4.2
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-755a18da0f2a481: Sentence determination (provision)
EXAMPLE 6:
Not terminating abbreviation within the sentence:
“The stakeholders are founding a Corp. and not an Inc.”
- bib.al.original-language: en
- bib.dp.publication-date: 2025-03-01
- ids.document: 100000012
- ids.tracing: hash-34512772D8710D9F3AE33C1475E9421C82959E5BF100B36A7B70DBB61673779B
- obj.clause-number: 9.4.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-9333ee66b8144a9: Sentence determination (provision)
Not terminating abbreviation within the sentence:
“The stakeholders are founding a Corp. and not an Inc.”
- bib.al.original-language: en
- bib.dp.publication-date: 2025-03-01
- ids.document: 100000012
- ids.tracing: hash-287FB87055FF6E6D4ABE4A4270F4A8B59713CBB603608AB13E99E7F18B319239
- obj.clause-number: 9.4.2
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-7ba03dd5f9964bf: Sentence determination (provision)
EXAMPLE 7:
Not terminating abbreviation within the sentence:
“The stakeholders are founding an Inc., but we need at least seven founding members.”
- bib.al.original-language: en
- bib.dp.publication-date: 2025-03-01
- ids.document: 100000012
- ids.tracing: hash-C1F1CD39178588213B48266DC2F13D8C3C2FD8F16D8254E87D511A2E7E029449
- obj.clause-number: 9.4.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-74a9234557b8409: Sentence determination (provision)
Not terminating abbreviation within the sentence:
“The stakeholders are founding an Inc., but we need at least seven founding members.
- bib.al.original-language: en
- bib.dp.publication-date: 2025-03-01
- ids.document: 100000012
- ids.tracing: hash-A406FEDE3A4AB000EF5402EF882A7E50498C042C39FA5F61F41FA866D1B3C656
- obj.clause-number: 9.4.2
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-7c69d23e5ffc42d: Sentence determination (provision)
EXAMPLE 8:
Terminating abbreviation at the end of the sentence:
“The stakeholders are founding an Inc. However, they need at least seven founding members.”
- bib.al.original-language: en
- bib.dp.publication-date: 2025-03-01
- ids.document: 100000012
- ids.tracing: hash-AD6A02CA842DCB4FFFCC2E04858C5CC73150807107179E0819E127DC39389178
- obj.clause-number: 9.4.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-1300dc06b3c2488: Sentence determination (provision)
Terminating abbreviation at the end of the sentence:
“The stakeholders are founding an Inc. However, they need at least seven founding members.”
- bib.al.original-language: en
- bib.dp.publication-date: 2025-03-01
- ids.document: 100000012
- ids.tracing: hash-FA1B51D4A7B059C4DCA6D3267D679EB94D32127E4492439BD1AC73AB8A5D32F7
- obj.clause-number: 9.4.2
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-7e0686dafd3a4e3: Sentence determination (provision)
EXAMPLE 9:
Not terminating decimal separator within the sentence:
“The users should ignore values below 4.1 °C in the measurements.”
- bib.al.original-language: en
- bib.dp.publication-date: 2025-03-01
- ids.document: 100000012
- ids.tracing: hash-7D4E94A98DF070E7155A5BC30069A2B50D88B333389199909EDB97A4105E89BB
- obj.clause-number: 9.4.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-cfd0312d76e3484: Sentence determination (provision)
Not terminating decimal separator within the sentence:
“The users should ignore values below 4.1 °C in the measurements.”
- bib.al.original-language: en
- bib.dp.publication-date: 2025-03-01
- ids.document: 100000012
- ids.tracing: hash-67EBADF08691FABB11B70D155AAD8FA349336E2EC26A45BD1159B90F8A5CC9F2
- obj.clause-number: 9.4.2
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-e7c099bf0e9844b: Sentence determination (provision)
EXAMPLE 10:
Not terminating specific technical notation within the sentence:
“If the router is set to the default gateway, the users can visit http://192.168.0.1 to access it.”
- bib.al.original-language: en
- bib.dp.publication-date: 2025-03-01
- ids.document: 100000012
- ids.tracing: hash-CDD0C17FD954DEA27247B818912E4EFE150066D32AF0BDF20C991488B23F1EA7
- obj.clause-number: 9.4.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-c4cc826ac7fe4d3: Sentence determination (provision)
Not terminating specific technical notation within the sentence:
“If the router is set to the default gateway, the users can visit http://192.168.0.1 to access it.”
- bib.al.original-language: en
- bib.dp.publication-date: 2025-03-01
- ids.document: 100000012
- ids.tracing: hash-CC931D424DA578582DF1C6C15FA783592293E5BE7F0888D3100BFB31734F91B2
- obj.clause-number: 9.4.2
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### R334: “Atomic element” (heading)
- bib.al.original-language: en
- bib.dp.publication-date: 2025-03-01
- ids.document: 100000012
- obj.clause-number: 9.4.3
- obj.element-name: heading
- obj.language: en
- obj.specobject-type: heading
- ChapterName: 9.4.3 “Atomic element”

##### prov-100000012-6945a0b99fd7404: “Atomic element” (provision)
The following elements shall not be split into sentences, so that no sentence is ripped-out of its logical context:
- elements of terminological entries up to any sub-entry, i. e. term, definition, and other information according to DIN ISO 10241-1;
- designation systems such as ordering details or standard designations (see Example);
- paired expressions and descriptions in descriptive enumerations;
- bibliographic entries in the list of documents;
- listings.
- bib.al.original-language: en
- bib.dp.publication-date: 2025-03-01
- ids.document: 100000012
- ids.tracing: hash-CCCECF7A7141F24345492A3D019080572277678BAACB40C88D17AD6E8B60248F
- obj.clause-number: 9.4.3
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-872a44317adb4fb: “Atomic element” (provision)
EXAMPLE:
“Screw ISO 1580-M5 × 20-4,8”
- bib.al.original-language: en
- bib.dp.publication-date: 2025-03-01
- ids.document: 100000012
- ids.tracing: hash-FC957C990221FEF18EF0424B497F1CF788C7B4FF3774386BBC8F703A99D264F3
- obj.clause-number: 9.4.3
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-2251db3aea594ee: “Atomic element” (provision)
“Screw ISO 1580-M5 × 20-4,8”
- bib.al.original-language: en
- bib.dp.publication-date: 2025-03-01
- ids.document: 100000012
- ids.tracing: hash-2D6A4FC484C19045F7C3AEEFD6EB1869DEB156A2FAA6D9A19D6416FDDC240875
- obj.clause-number: 9.4.3
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### R338: “Terminating element” (heading)
- bib.al.original-language: en
- bib.dp.publication-date: 2025-03-01
- ids.document: 100000012
- obj.clause-number: 9.4.4
- obj.element-name: heading
- obj.language: en
- obj.specobject-type: heading
- ChapterName: 9.4.4 “Terminating element”

##### prov-100000012-68f95e8e43f843b: “Terminating element” (provision)
Sentences shall be terminated by the following elements, so that no expression can run out of its logical context:
- “atomic element” (see 9.4.3);
- figure;
- example;
- note;
- division (all types of clauses, annexes, and terminological entries);
- table;
- warning.
- bib.al.original-language: en
- bib.dp.publication-date: 2025-03-01
- ids.document: 100000012
- ids.tracing: hash-E79A7BE1359E3C93393B6C11A820385A1C6D490673586CCAB31DBE0A3608A3A0
- obj.clause-number: 9.4.4
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R334

#### R340: Enumerations (lists) in the text (heading)
- bib.al.original-language: en
- bib.dp.publication-date: 2025-03-01
- ids.document: 100000012
- obj.clause-number: 9.4.5
- obj.element-name: heading
- obj.language: en
- obj.specobject-type: heading
- ChapterName: 9.4.5 Enumerations (lists) in the text

##### R341: Enumeration as part of a provision (heading)
- bib.al.original-language: en
- bib.dp.publication-date: 2025-03-01
- ids.document: 100000012
- obj.clause-number: 9.4.5.1
- obj.element-name: heading
- obj.language: en
- obj.specobject-type: heading
- ChapterName: 9.4.5.1 Enumeration as part of a provision

###### prov-100000012-009cb3e11ffa41f: Enumeration as part of a provision (provision)
If the sentence runs from an introductory paragraph text into the enumeration (see Example 1), either:
- the paragraph and whole enumeration shall be output with all items as one SpecObject; or
- the introductory paragraph may be moved at the beginning of each item (see Example 2) so that each item may be handled as separate provision (see 9.4.5.2) if the users prefer normalized provisions.
- bib.al.original-language: en
- bib.dp.publication-date: 2025-03-01
- ids.document: 100000012
- ids.tracing: hash-D82BB2DFA42303412B2E6A733B84CFF6710FF39E064E75A0B860AFAC394D54F2
- obj.clause-number: 9.4.5.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-ce758f0d900d4d7
- cross-reference -> prov-100000012-d2a3523543074f4
- cross-reference -> R348

###### prov-100000012-ce758f0d900d4d7: Enumeration as part of a provision (provision)
EXAMPLE 1:
Enumeration is part of a provision:
“The test report shall include the following information:
- a) the sample location on the sample piece from which the microsection was made;
- b) the coating thickness measured at each location (7.3) in µm (in mm if greater than 1 mm) and the length of the section over which the measurement was made;
- c) the local coating thickness, i. e. the arithmetic mean value of the measured coating thicknesses.”
- bib.al.original-language: en
- bib.dp.publication-date: 2025-03-01
- ids.document: 100000012
- ids.tracing: hash-C09D7F8FAA9EC6BD6E6E82EDBC5AC084C3CBCD95855D72CDECA9C40453295701
- obj.clause-number: 9.4.5.1
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> R76

###### prov-100000012-3e696ef91dd74e8: Enumeration as part of a provision (provision)
Enumeration is part of a provision:
- bib.al.original-language: en
- bib.dp.publication-date: 2025-03-01
- ids.document: 100000012
- ids.tracing: hash-3478359F91FC8DADFF5856FE3B23E596D7966716B444375453EEBDE32817215C
- obj.clause-number: 9.4.5.1
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-94f1f2df5fac45a: Enumeration as part of a provision (provision)
“The test report shall include the following information:
- a) the sample location on the sample piece from which the microsection was made;
- b) the coating thickness measured at each location (7.3) in µm (in mm if greater than 1 mm) and the length of the section over which the measurement was made;
- c) the local coating thickness, i. e. the arithmetic mean value of the measured coating thicknesses.”
- bib.al.original-language: en
- bib.dp.publication-date: 2025-03-01
- ids.document: 100000012
- ids.tracing: hash-8867F3191C039B5AC0F6BBD31CE1B2063CDB2A80732388F2E2B598E85904F4F9
- obj.clause-number: 9.4.5.1
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-d2a3523543074f4: Enumeration as part of a provision (provision)
EXAMPLE 2:
Original non-singular provision and normalized singular provisions:
| original paragraph with a list in the source | normalized provisions in the target |
| --- | --- |
| “The organization shall retain documented information: - a on the results of the review; - b on any new requirements for the products and services.” | - a “The organization shall retain documented information on the results of the review. - b The organization shall retain documented information on any new requirements for the products and services.” |
- bib.al.original-language: en
- bib.dp.publication-date: 2025-03-01
- ids.document: 100000012
- ids.tracing: hash-E28B9D1B06223E6F37034CE95E9C2C14C3A942BB784978F0EE2FF0549370605F
- obj.clause-number: 9.4.5.1
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-2498bea894dd494: Enumeration as part of a provision (provision)
Original non-singular provision and normalized singular provisions:
- bib.al.original-language: en
- bib.dp.publication-date: 2025-03-01
- ids.document: 100000012
- ids.tracing: hash-9A7AED4AE760367C722195B9F7B9806B5A9FB349A969B4DD56F6E7250424E2FE
- obj.clause-number: 9.4.5.1
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### R348: Each item of an enumeration as a separate provision (heading)
- bib.al.original-language: en
- bib.dp.publication-date: 2025-03-01
- ids.document: 100000012
- obj.clause-number: 9.4.5.2
- obj.element-name: heading
- obj.language: en
- obj.specobject-type: heading
- ChapterName: 9.4.5.2 Each item of an enumeration as a separate provision

###### prov-100000012-d2b1d549431b464: Each item of an enumeration as a separate provision (provision)
If each item of an enumeration is recognized as a complete sentence (see Example), for the whole enumeration each item shall be output as a separate SpecObject.
- bib.al.original-language: en
- bib.dp.publication-date: 2025-03-01
- ids.document: 100000012
- ids.tracing: hash-2D87D8460BF43037C1DD41A0569B579FF2F50817FF3697B524700AB7697C9690
- obj.clause-number: 9.4.5.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### prov-100000012-4bed7c2afd3347c: Each item of an enumeration as a separate provision (provision)
The context of the enumeration should be retained as a relationship to a parent container SpecObject.
- bib.al.original-language: en
- bib.dp.publication-date: 2025-03-01
- ids.document: 100000012
- ids.tracing: hash-7B9DD326B6D29F51281040386C8332508E16AF81125244802E85618196516399
- obj.clause-number: 9.4.5.2
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

###### prov-100000012-99740a570c9c400: Each item of an enumeration as a separate provision (provision)
If criteria for both methods are met, the first method has priority, and the whole enumeration should be handled as one SpecObject (see 9.4.5.1).
- bib.al.original-language: en
- bib.dp.publication-date: 2025-03-01
- ids.document: 100000012
- ids.tracing: hash-175884D9DAA51BC658619120FB68C79C7D1D273FE5BC48642D05EF7A2DD8A7D2
- obj.clause-number: 9.4.5.2
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R341

###### prov-100000012-a6695b6a215a436: Each item of an enumeration as a separate provision (provision)
EXAMPLE:
Each item of an enumeration is a separate provision:
“The test procedure shall be performed as follows:
- a) The user shall switch on the device.
- b) The user shall insert the test object.
- c) The user shall press the start button.
- d) The user shall document the test results.
- e) The user shall remove the test object.
- f) The user shall switch off the device.”
- bib.al.original-language: en
- bib.dp.publication-date: 2025-03-01
- ids.document: 100000012
- ids.tracing: hash-6F10322E5185D95A35B57227AF30DA38E800F276A2495CB26202887DC522664B
- obj.clause-number: 9.4.5.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-f14adc75cb5844f: Each item of an enumeration as a separate provision (provision)
Each item of an enumeration is a separate provision:
“The test procedure shall be performed as follows:
- a) The user shall switch on the device.
- b) The user shall insert the test object.
- c) The user shall press the start button.
- d) The user shall document the test results.
- e) The user shall remove the test object.
- f) The user shall switch off the device.”
- bib.al.original-language: en
- bib.dp.publication-date: 2025-03-01
- ids.document: 100000012
- ids.tracing: hash-17AB7F8374849FEA977F22AB614C52AA60E2B1D20EB3F21915FC4A02E411A7CF
- obj.clause-number: 9.4.5.2
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### R354: Modality; bindingness (heading)
- bib.al.original-language: en
- bib.dp.publication-date: 2025-03-01
- ids.document: 100000012
- obj.clause-number: 9.5
- obj.element-name: heading
- obj.language: en
- obj.specobject-type: heading
- ChapterName: 9.5 Modality; bindingness

#### R355: Determining the modality (obj.modality) (heading)
- bib.al.original-language: en
- bib.dp.publication-date: 2025-03-01
- ids.document: 100000012
- obj.clause-number: 9.5.1
- obj.element-name: heading
- obj.language: en
- obj.specobject-type: heading
- ChapterName: 9.5.1 Determining the modality (obj.modality)

##### prov-100000012-4f651f3be875480: Determining the modality (obj.modality) (provision)
The values of the attribute obj.modality (8.2.1.2) shall be determined for each sentence of the public standard (see 9.2.1).
- bib.al.original-language: en
- bib.dp.publication-date: 2025-03-01
- ids.document: 100000012
- ids.tracing: hash-DA5ADCF81026CF9783050FC0E4E4B8B3016B92CC175612A84047D06E9DE324E3
- obj.clause-number: 9.5.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124
- cross-reference -> R238

##### prov-100000012-fb0fba76be064fb: Determining the modality (obj.modality) (provision)
Depending on the selected level of fragmentation (see 9.2.1) of the public standard, the resulting values of the attribute obj.modality (8.2.1.2) of the SpecObject shall be determined according to 9.5.2.
- bib.al.original-language: en
- bib.dp.publication-date: 2025-03-01
- ids.document: 100000012
- ids.tracing: hash-8B78F7C603AE51F273AA77CD7030FEA9158D1FFD637C3B13BF05D410A80A2192
- obj.clause-number: 9.5.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R238
- cross-reference -> R124
- cross-reference -> R361

##### prov-100000012-feb4566c0a1f4c4: Determining the modality (obj.modality) (provision)
The values of the attribute obj.modality (8.2.1.2) shall be selected from 8.3.3 according to the ISO/IEC Directives, Part 2.
- bib.al.original-language: en
- bib.dp.publication-date: 2025-03-01
- ids.document: 100000012
- ids.tracing: hash-6A547601F0C2079718A293E92FDA8D310C2C2BB692E4F5F40D59228AED859235
- obj.clause-number: 9.5.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124
- cross-reference -> R147

##### prov-100000012-c517abc5686d466: Determining the modality (obj.modality) (provision)
If the values of the attribute obj.modality (8.2.1.2) has been determined using natural language processing, the attribute obj.modality (8.2.1.2) shall be set to a value according to 8.3.3:
- If the actual fragment contains two or more different modalities, the modality shall be interpreted as the value “ambiguous”.
- If the actual fragment contains the modality for a capability or possibility, the modality may be assumed as the value “possibility”.
- If the actual fragment contains the modality for an external constraint or a requirement, the modality may be assumed as the value “requirement”.
- If no modality could be determined for the actual fragment, the modality shall be interpreted as the value “undefined” (equivalent to “statement” according to the ISO/IEC Directives, Part 2).
- bib.al.original-language: en
- bib.dp.publication-date: 2025-03-01
- ids.document: 100000012
- ids.tracing: hash-EDB6E9577511C0BB0A683AC92D3F1824812FCD63B8E9C8C12C1D23853B6EB651
- obj.clause-number: 9.5.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124
- cross-reference -> R147

###### prov-100000012-725f09f3812948a: Determining the modality (obj.modality), Note (provision)
NOTE:
Although an external constrains is formally not a modality, the obj.modality (8.2.1.2) contains the value “constraint” since the attribute represents not only modalities but all levels of obligations for the user.
- bib.al.original-language: en
- bib.dp.publication-date: 2025-03-01
- ids.document: 100000012
- ids.tracing: hash-DBC686FCDA8F4328449545BBDB00EFE003C152C9B50DDBC9575F91BA36CB0391
- obj.clause-number: 9.5.1
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> R124

#### R361: Modalities related to context (heading)
- bib.al.original-language: en
- bib.dp.publication-date: 2025-03-01
- ids.document: 100000012
- obj.clause-number: 9.5.2
- obj.element-name: heading
- obj.language: en
- obj.specobject-type: heading
- ChapterName: 9.5.2 Modalities related to context

##### prov-100000012-6d81461fdc0f497: Modalities related to context (provision)
- To classify sentences, the attribute obj.modality (8.2.1.2) shall be set to the value determined for the sentence.
- To classify paragraphs, the attribute obj.modality (8.2.1.2) shall be set to the value for the highest bindingness (see 9.5.3) of the sentences contained in the paragraph.
- To classify divisions, the attribute obj.modality (8.2.1.2) shall be set to the value for the highest bindingness (see 9.5.3) of the sentences contained in the division.
- bib.al.original-language: en
- bib.dp.publication-date: 2025-03-01
- ids.document: 100000012
- ids.tracing: hash-823250F8B87EB5E16044DDCFC03F6A26BC66BCC3AA8113B8F0AD0BE28FFAE3FB
- obj.clause-number: 9.5.2
- obj.element-name: unordered-list
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-100000012-f2b15832085146f: Modalities related to context, list extract (provision)
| → | To classify sentences, the attribute obj.modality (8.2.1.2) shall be set to the value determined for the sentence. |
| --- | --- |
- bib.al.original-language: en
- bib.dp.publication-date: 2025-03-01
- ids.document: 100000012
- ids.tracing: hash-15B2C1B5C2E2682C498862891E6D0D47B312EA427D0FC2B3178F39BC79AF20FC
- obj.clause-number: 9.5.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124

###### prov-100000012-46acc4375e32484: Modalities related to context, list extract (provision)
| → | To classify paragraphs, the attribute obj.modality (8.2.1.2) shall be set to the value for the highest bindingness (see 9.5.3) of the sentences contained in the paragraph. |
| --- | --- |
- bib.al.original-language: en
- bib.dp.publication-date: 2025-03-01
- ids.document: 100000012
- ids.tracing: hash-8118888062D623C91846229F5691AB97633C5C1DAB62E16A1845865CD2358328
- obj.clause-number: 9.5.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124
- cross-reference -> R373

###### prov-100000012-610c353faecf4c9: Modalities related to context, list extract (provision)
| → | To classify divisions, the attribute obj.modality (8.2.1.2) shall be set to the value for the highest bindingness (see 9.5.3) of the sentences contained in the division. |
| --- | --- |
- bib.al.original-language: en
- bib.dp.publication-date: 2025-03-01
- ids.document: 100000012
- ids.tracing: hash-2939037327FC8AF8D60CFA0228105B20958061A66529BDF72C7FD63E82544820
- obj.clause-number: 9.5.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124
- cross-reference -> R373

##### prov-100000012-49b19c228a73426: Modalities related to context (provision)
EXAMPLE:
- If a paragraph contains several sentences using the division-wise output (see 9.4.1.1), the sentence with the highest bindingness determines the modality of the SpecObject. This means that if the division contains at least one requirement, the whole division shall be classified as a requirement.
- If a paragraph contains several sentences using a paragraph-wise output (see 9.4.1.2), the sentence with the highest binding determines the modality of the SpecObject. This means that if the paragraph contains at least one requirement, the whole paragraph shall be classified as a requirement.
- If a sentence is one of more sentences of an atomic element (see 9.4.3) using the standard sentence-wise output (see 9.4.1.3), the sentence with the highest bindingness determines the modality of the SpecObject. This means that if the element contains at least one requirement, the whole element shall be classified as a requirement.
- bib.al.original-language: en
- bib.dp.publication-date: 2025-03-01
- ids.document: 100000012
- ids.tracing: hash-8CA4D9F4DCE01CE8216E08005C390A6459E23DB663347A577D20EBC46ABC3655
- obj.clause-number: 9.5.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-ae8b0b035dec44a: Modalities related to context, list extract (provision)
| → | If a paragraph contains several sentences using the division-wise output (see 9.4.1.1), the sentence with the highest bindingness determines the modality of the SpecObject. |
| --- | --- |
- bib.al.original-language: en
- bib.dp.publication-date: 2025-03-01
- ids.document: 100000012
- ids.tracing: hash-AAA857040588D92D2DCB3A19ECCAB03DC496CB89B7C7AB4064C354A57819080A
- obj.clause-number: 9.5.2
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> R302

###### prov-100000012-75af1b766153437: Modalities related to context, list extract (provision)
| → | This means that if the division contains at least one requirement, the whole division shall be classified as a requirement. |
| --- | --- |
- bib.al.original-language: en
- bib.dp.publication-date: 2025-03-01
- ids.document: 100000012
- ids.tracing: hash-CF8088D890FF6EE117F31C3E4CD3FC4754FCE5530330CC1FB036463A181B47CE
- obj.clause-number: 9.5.2
- obj.element-name: paragraph
- obj.language: en
- obj.modality: requirement
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-e0a6874cc5884e1: Modalities related to context, list extract (provision)
| → | If a paragraph contains several sentences using a paragraph-wise output (see 9.4.1.2), the sentence with the highest binding determines the modality of the SpecObject. |
| --- | --- |
- bib.al.original-language: en
- bib.dp.publication-date: 2025-03-01
- ids.document: 100000012
- ids.tracing: hash-738EFD5A8E3AAC0E6663B3571D7756D0F2D7DE78E85B1FF81DC9A6AA7BDE9203
- obj.clause-number: 9.5.2
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> R304

###### prov-100000012-35729264c5624a5: Modalities related to context, list extract (provision)
| → | This means that if the paragraph contains at least one requirement, the whole paragraph shall be classified as a requirement. |
| --- | --- |
- bib.al.original-language: en
- bib.dp.publication-date: 2025-03-01
- ids.document: 100000012
- ids.tracing: hash-3087C20F909C68F1C152BFBCAB42949C16D6C9DE3D50E6E3CC42C3151FAE36F6
- obj.clause-number: 9.5.2
- obj.element-name: paragraph
- obj.language: en
- obj.modality: requirement
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-cfe95d1da437466: Modalities related to context, list extract (provision)
| → | If a sentence is one of more sentences of an atomic element (see 9.4.3) using the standard sentence-wise output (see 9.4.1.3), the sentence with the highest bindingness determines the modality of the SpecObject. |
| --- | --- |
- bib.al.original-language: en
- bib.dp.publication-date: 2025-03-01
- ids.document: 100000012
- ids.tracing: hash-8C1115FB71E90BD39E990C4EAD91DAB0DB170F5983E0D171465B1401379355B7
- obj.clause-number: 9.5.2
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> R334
- cross-reference -> R306

###### prov-100000012-6f68373d0762433: Modalities related to context, list extract (provision)
| → | This means that if the element contains at least one requirement, the whole element shall be classified as a requirement. |
| --- | --- |
- bib.al.original-language: en
- bib.dp.publication-date: 2025-03-01
- ids.document: 100000012
- ids.tracing: hash-F9EB46B33A9644ACB3D0DD85CA1DC484287D559B1C9148391B5172E52844B939
- obj.clause-number: 9.5.2
- obj.element-name: paragraph
- obj.language: en
- obj.modality: requirement
- obj.normativity: informative
- obj.specobject-type: provision
- use.business-process: undefined
- use.business-sector: undefined
- use.interaction: undefined
- use.location: undefined
- use.product-category: undefined
- use.product-life-cycle: undefined
- use.project-phase: undefined
- use.purpose: undefined

#### R373: Bindingness of the modality values (heading)
- bib.al.original-language: en
- bib.dp.publication-date: 2025-03-01
- ids.document: 100000012
- obj.clause-number: 9.5.3
- obj.element-name: heading
- obj.language: en
- obj.specobject-type: heading
- ChapterName: 9.5.3 Bindingness of the modality values

##### prov-100000012-c013d891a6ff485: Bindingness of the modality values (provision)
The values of the attribute obj.modality (8.2.1.2) are listed from the highest (1) to the lowest (9) bindingness:
1. constraint;
2. requirement;
3. recommendation;
4. capability;
5. permission;
6. possibility;
7. ambiguous;
8. undefined (statement);
9. value for the attribute has not been determined.
- bib.al.original-language: en
- bib.dp.publication-date: 2025-03-01
- ids.document: 100000012
- ids.tracing: hash-213FDB7FEC7FA6E756CF7670613D1197484779153A3D043782136010FCB0567E
- obj.clause-number: 9.5.3
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124

#### R375: Review of the modality (obj.modality) (heading)
- bib.al.original-language: en
- bib.dp.publication-date: 2025-03-01
- ids.document: 100000012
- obj.clause-number: 9.5.4
- obj.element-name: heading
- obj.language: en
- obj.specobject-type: heading
- ChapterName: 9.5.4 Review of the modality (obj.modality)

##### prov-100000012-a7c072f0539c464: Review of the modality (obj.modality) (provision)
- If the attribute obj.modality (8.2.1.2) has been determined using natural language processing, the user shall validate ambiguous and uncertain values during the review of the ReqIF™ (see 9.5.5).
- If the attribute obj.modality (8.2.1.2) has been determined using natural language processing, the supplier should support the user review with additional information about the reliability of the recognized modality for each SpecObject in the ReqIF™ file (see 9.7.3).
- bib.al.original-language: en
- bib.dp.publication-date: 2025-03-01
- ids.document: 100000012
- ids.tracing: hash-78885B7390F87B91F1D8B69F621232D44F33BCAF3A4606929CB93F544540342E
- obj.clause-number: 9.5.4
- obj.element-name: unordered-list
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-100000012-a8b1b247c922493: Review of the modality (obj.modality), list extract (provision)
| → | If the attribute obj.modality (8.2.1.2) has been determined using natural language processing, the user shall validate ambiguous and uncertain values during the review of the ReqIF™ (see 9.5.5). |
| --- | --- |
- bib.al.original-language: en
- bib.dp.publication-date: 2025-03-01
- ids.document: 100000012
- ids.tracing: hash-C80EF7BD01DDAB6B511BBCBA1D231AC1F0DCF4FE0CA1132AF20791B580C84901
- obj.clause-number: 9.5.4
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124
- cross-reference -> R381

###### prov-100000012-4206bb77618f424: Review of the modality (obj.modality), list extract (provision)
| → | If the attribute obj.modality (8.2.1.2) has been determined using natural language processing, the supplier should support the user review with additional information about the reliability of the recognized modality for each SpecObject in the ReqIF™ file (see 9.7.3). |
| --- | --- |
- bib.al.original-language: en
- bib.dp.publication-date: 2025-03-01
- ids.document: 100000012
- ids.tracing: hash-44D28D8FC801FEA65F257B5EF4962E1442A4101C30DBE5AE8710C7B3BCD02F47
- obj.clause-number: 9.5.4
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124
- cross-reference -> R412

##### prov-100000012-540ebc2f7d0f45d: Review of the modality (obj.modality) (provision)
Since users may not blindly rely on automatically determined results from post-processing services, the user is responsible to review each SpecObject in the ReqIF™ file which is the result of such post-processing.
- bib.al.original-language: en
- bib.dp.publication-date: 2025-03-01
- ids.document: 100000012
- ids.tracing: hash-85081D87D9D626D710F01104ECBDEED5A619FF8785886F51D3071912934FA53D
- obj.clause-number: 9.5.4
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-560000149eb44cd: Review of the modality (obj.modality) (provision)
If the service deliverable has been confirmed by the authority responsible for the public standard, users may assume a high reliability of a service.
- bib.al.original-language: en
- bib.dp.publication-date: 2025-03-01
- ids.document: 100000012
- ids.tracing: hash-244496396AC8D16044133B5FA001041C0F18A853E4895CB789305FEC9308CE25
- obj.clause-number: 9.5.4
- obj.element-name: paragraph
- obj.language: en
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

#### R381: Align the modality (obj.modality) (heading)
- bib.al.original-language: en
- bib.dp.publication-date: 2025-03-01
- ids.document: 100000012
- obj.clause-number: 9.5.5
- obj.element-name: heading
- obj.language: en
- obj.specobject-type: heading
- ChapterName: 9.5.5 Align the modality (obj.modality)

##### prov-100000012-f5767e5af65c465: Align the modality (obj.modality) (provision)
- If capabilities and possibilities are required differentiated, the user shall align the attribute obj.modality (8.2.1.2) to the according value (see 8.3.3).
- If external constraints and requirements are required differentiated, the user shall align the attribute obj.modality (8.2.1.2) to the according value (see 8.3.3).
- If modality is ambiguous, missing or undefined, the user shall align the attribute obj.modality (8.2.1.2) to the according value (see 8.3.3).
- bib.al.original-language: en
- bib.dp.publication-date: 2025-03-01
- ids.document: 100000012
- ids.tracing: hash-10D14FCEA46593A27726EA04BE87ED7E73D4E79B796EA966A137AB185E6043A0
- obj.clause-number: 9.5.5
- obj.element-name: unordered-list
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-100000012-b7b4795df4be4ac: Align the modality (obj.modality), list extract (provision)
| → | If capabilities and possibilities are required differentiated, the user shall align the attribute obj.modality (8.2.1.2) to the according value (see 8.3.3). |
| --- | --- |
- bib.al.original-language: en
- bib.dp.publication-date: 2025-03-01
- ids.document: 100000012
- ids.tracing: hash-AA4C186D3A0500E21E599818DD0B280FFAF7836142DC5D2576B955C5FCC502BB
- obj.clause-number: 9.5.5
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124
- cross-reference -> R147

###### prov-100000012-2cdb05a409844f9: Align the modality (obj.modality), list extract (provision)
| → | If external constraints and requirements are required differentiated, the user shall align the attribute obj.modality (8.2.1.2) to the according value (see 8.3.3). |
| --- | --- |
- bib.al.original-language: en
- bib.dp.publication-date: 2025-03-01
- ids.document: 100000012
- ids.tracing: hash-BFD1C13BE9772E26A3B2FD9FF192B3FC3A6575520199DBA48DAA96D2CDDFC140
- obj.clause-number: 9.5.5
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124
- cross-reference -> R147

###### prov-100000012-f610bd008b8e497: Align the modality (obj.modality), list extract (provision)
| → | If modality is ambiguous, missing or undefined, the user shall align the attribute obj.modality (8.2.1.2) to the according value (see 8.3.3). |
| --- | --- |
- bib.al.original-language: en
- bib.dp.publication-date: 2025-03-01
- ids.document: 100000012
- ids.tracing: hash-66E35EAE2DCCB2D7E84DEC3EC96BB196FBAF4C4C646E899BC4B052A3C0A397A0
- obj.clause-number: 9.5.5
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124
- cross-reference -> R147

### R386: Content attributes (ReqIF.*) (heading)
- bib.al.original-language: en
- bib.dp.publication-date: 2025-03-01
- ids.document: 100000012
- obj.clause-number: 9.6
- obj.element-name: heading
- obj.language: en
- obj.specobject-type: heading
- ChapterName: 9.6 Content attributes (ReqIF.*)

#### R387: Heading (ReqIF.ChapterName) (heading)
- bib.al.original-language: en
- bib.dp.publication-date: 2025-03-01
- ids.document: 100000012
- obj.clause-number: 9.6.1
- obj.element-name: heading
- obj.language: en
- obj.specobject-type: heading
- ChapterName: 9.6.1 Heading (ReqIF.ChapterName)

##### prov-100000012-104e09839127441: Heading (ReqIF.ChapterName) (provision)
The heading of the SpecObject shall be output as value of the attribute ReqIF.ChapterName (9.6.1) according to 9.1.
- bib.al.original-language: en
- bib.dp.publication-date: 2025-03-01
- ids.document: 100000012
- ids.tracing: hash-5BCDDA781E650588E7C42A37D9107FED72F510EE47AAFFEF524B1ADB5B9E50B1
- obj.clause-number: 9.6.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R387
- cross-reference -> R206

##### prov-100000012-6940693b17e347e: Heading (ReqIF.ChapterName) (provision)
If given in the source document, the original labelling and numbering of the public standard shall be output according to 10.2.
- bib.al.original-language: en
- bib.dp.publication-date: 2025-03-01
- ids.document: 100000012
- ids.tracing: hash-3E5988406571D8BD37A281C2CF00AD10D0151822AB2295DECE892D42204A1CD9
- obj.clause-number: 9.6.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R546

##### prov-100000012-8a8455b1f29b47e: Heading (ReqIF.ChapterName) (provision)
If the value of ReqIF.ChapterName (9.6.1) shall be set, the value of ReqIF.Text (9.6.2) shall not be set.
- bib.al.original-language: en
- bib.dp.publication-date: 2025-03-01
- ids.document: 100000012
- ids.tracing: hash-F279B68F3D33735B7529C9FE317C6202599DC153DFE0DDE2D441334E600DBC3A
- obj.clause-number: 9.6.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R387
- cross-reference -> R393

##### prov-100000012-f63d9fd41bb240f: Heading (ReqIF.ChapterName) (provision)
EXAMPLE:
Output for the heading of the clause “1 Scope”:
- ReqIF.ChapterName: “1 Scope”;
- ReqIF.Text: not set;
- obj.clause-heading: “Scope”;
- obj.clause-number: “1”.
- bib.al.original-language: en
- bib.dp.publication-date: 2025-03-01
- ids.document: 100000012
- ids.tracing: hash-13FF0AA791AB0FDFC85BC02EEA64F28785E3E8F15F7AA3BA829AAD78768C60C7
- obj.clause-number: 9.6.1
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-c3f37975c8854a1: Heading (ReqIF.ChapterName) (provision)
Output for the heading of the clause “1 Scope”:
- ReqIF.ChapterName: “1 Scope”;
- ReqIF.Text: not set;
- obj.clause-heading: “Scope”;
- obj.clause-number: “1”.
- bib.al.original-language: en
- bib.dp.publication-date: 2025-03-01
- ids.document: 100000012
- ids.tracing: hash-269E81D8D38473EB967CBC2E1F9A6AA6B1C07A0A9D1E60A1DB6D958EE044C570
- obj.clause-number: 9.6.1
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### R393: Content (ReqIF.Text) (heading)
- bib.al.original-language: en
- bib.dp.publication-date: 2025-03-01
- ids.document: 100000012
- obj.clause-number: 9.6.2
- obj.element-name: heading
- obj.language: en
- obj.specobject-type: heading
- ChapterName: 9.6.2 Content (ReqIF.Text)

##### prov-100000012-52c988d7fa47488: Content (ReqIF.Text) (provision)
The content of the SpecObject shall be output as value of the attribute ReqIF.Text (9.6.2).
- bib.al.original-language: en
- bib.dp.publication-date: 2025-03-01
- ids.document: 100000012
- ids.tracing: hash-72892C365959FA51C14C8103CB56B35205DA1EDE823B6D463F6292F4C2598716
- obj.clause-number: 9.6.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R393

##### prov-100000012-14802a1b6a3b46d: Content (ReqIF.Text) (provision)
If given in the source document, the original labelling and numbering of the public standard shall be output according to 10.2.
- bib.al.original-language: en
- bib.dp.publication-date: 2025-03-01
- ids.document: 100000012
- ids.tracing: hash-B91C956F3FF1AF227427F1B5D7655FE1E210F5DC8F6183C95556E29E6838F904
- obj.clause-number: 9.6.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R546

##### prov-100000012-7c57f75387654f9: Content (ReqIF.Text) (provision)
If the value of ReqIF.Text (9.6.2) shall be set, the value of ReqIF.ChapterName (9.6.1) shall not be set.
- bib.al.original-language: en
- bib.dp.publication-date: 2025-03-01
- ids.document: 100000012
- ids.tracing: hash-45829A3C1925FDE0C38C1556421E3A85545057916DDDD5169F311B296ACE84BB
- obj.clause-number: 9.6.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R393
- cross-reference -> R387

##### prov-100000012-af68b14a08134bc: Content (ReqIF.Text) (provision)
EXAMPLE:
Output for the element “WARNING: This mixture can be explosively unstable, particularly if heated.” specified within Annex B “Some typical etchants for use at room temperature”:
- ReqIF.ChapterName: not set;
- ReqIF.Text: “WARNING: This mixture can be explosively unstable, particularly if heated.”.
- bib.al.original-language: en
- bib.dp.publication-date: 2025-03-01
- ids.document: 100000012
- ids.tracing: hash-E2A7BF222B394D4A7B5D76E9A4BFD629D49B9FF02FB412B23BC39FFF3DBFCA93
- obj.clause-number: 9.6.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-bbb29047c68f460: Content (ReqIF.Text) (provision)
Output for the element “WARNING: This mixture can be explosively unstable, particularly if heated.” specified within Annex B “Some typical etchants for use at room temperature”:
- ReqIF.ChapterName: not set;
- ReqIF.Text: “WARNING: This mixture can be explosively unstable, particularly if heated.”.
- bib.al.original-language: en
- bib.dp.publication-date: 2025-03-01
- ids.document: 100000012
- ids.tracing: hash-172E5E5EAC0FA29DDDCD98598ADE1109644BA12A5129844C4EF2B22CF87C9FC7
- obj.clause-number: 9.6.2
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> R628

### R399: Object attributes (obj.*) (heading)
- bib.al.original-language: en
- bib.dp.publication-date: 2025-03-01
- ids.document: 100000012
- obj.clause-number: 9.7
- obj.element-name: heading
- obj.language: en
- obj.specobject-type: heading
- ChapterName: 9.7 Object attributes (obj.*)

#### R400: Clause heading (obj.clause-heading) (heading)
- bib.al.original-language: en
- bib.dp.publication-date: 2025-03-01
- ids.document: 100000012
- obj.clause-number: 9.7.1
- obj.element-name: heading
- obj.language: en
- obj.specobject-type: heading
- ChapterName: 9.7.1 Clause heading (obj.clause-heading)

##### prov-100000012-fcb320fcb32c4ac: Clause heading (obj.clause-heading) (provision)
If given in the source document, the original heading of the parent division in the public standard shall be output as value of the attribute obj.clause-heading (8.2.1.2) according to 9.1.
- bib.al.original-language: en
- bib.dp.publication-date: 2025-03-01
- ids.document: 100000012
- ids.tracing: hash-4FF1C91A5F2A8F0EF3381C2D2C04B12349F9D3E558BAE08E2A7D4AEADC420DC9
- obj.clause-number: 9.7.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124
- cross-reference -> R206

##### prov-100000012-9f2058135bd2405: Clause heading (obj.clause-heading) (provision)
EXAMPLE 1:
Output for the heading of the clause “1 Scope”:
- obj.clause-heading: “Scope”;
- obj.clause-number: “1”.
- bib.al.original-language: en
- bib.dp.publication-date: 2025-03-01
- ids.document: 100000012
- ids.tracing: hash-76349057F08F87FAD1B71CCC376699E55D8993C78E8F111F2CAE0311742865DD
- obj.clause-number: 9.7.1
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-c6dc1890289446f: Clause heading (obj.clause-heading) (provision)
Output for the heading of the clause “1 Scope”:
- obj.clause-heading: “Scope”;
- obj.clause-number: “1”.
- bib.al.original-language: en
- bib.dp.publication-date: 2025-03-01
- ids.document: 100000012
- ids.tracing: hash-C78CE55DA497D9E3AF79A6EA407C5B141A959751D93427DDB2CFD86CD4497211
- obj.clause-number: 9.7.1
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-e36389a8a74e459: Clause heading (obj.clause-heading) (provision)
EXAMPLE 2:
Output for the element “WARNING: This mixture can be explosively unstable, particularly if heated.” specified within Annex B “Some typical etchants for use at room temperature”:
- obj.clause-heading: “Some typical etchants for use at room temperature”;
- obj.clause-number: “Annex B”.
- bib.al.original-language: en
- bib.dp.publication-date: 2025-03-01
- ids.document: 100000012
- ids.tracing: hash-34F618095BAB592F80A2D9499F6094D9296C14FC71F8EEBDC66878D2E741B51B
- obj.clause-number: 9.7.1
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> R628

###### prov-100000012-31cdfce6c79e4f3: Clause heading (obj.clause-heading) (provision)
Output for the element “WARNING: This mixture can be explosively unstable, particularly if heated.” specified within Annex B “Some typical etchants for use at room temperature”:
- obj.clause-heading: “Some typical etchants for use at room temperature”;
- obj.clause-number: “Annex B”.
- bib.al.original-language: en
- bib.dp.publication-date: 2025-03-01
- ids.document: 100000012
- ids.tracing: hash-72E085EC3747B21B58700DE184E3479EA6C9C98F41A5BD3C2958416047D73905
- obj.clause-number: 9.7.1
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> R628

#### R406: Clause context (obj.clause-number) (heading)
- bib.al.original-language: en
- bib.dp.publication-date: 2025-03-01
- ids.document: 100000012
- obj.clause-number: 9.7.2
- obj.element-name: heading
- obj.language: en
- obj.specobject-type: heading
- ChapterName: 9.7.2 Clause context (obj.clause-number)

##### prov-100000012-9ee88512d2a2436: Clause context (obj.clause-number) (provision)
If given in the source document, the original labelling and numbering of the parent division in the public standard shall be output as value of the attribute obj.clause-number (8.2.1.2) according to 9.1.
- bib.al.original-language: en
- bib.dp.publication-date: 2025-03-01
- ids.document: 100000012
- ids.tracing: hash-C222201554469CFE0A4B4099BF8E9F1283EB47ABDF82755A0F192077FC5D4039
- obj.clause-number: 9.7.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124
- cross-reference -> R206

##### prov-100000012-8c6df52c32d94d6: Clause context (obj.clause-number) (provision)
EXAMPLE 1:
Output for the heading of the clause “1 Scope”:
- obj.clause-heading: “Scope”;
- obj.clause-number: “1”.
- bib.al.original-language: en
- bib.dp.publication-date: 2025-03-01
- ids.document: 100000012
- ids.tracing: hash-341C5A31A25B8511CC7B483A862E7F0F325BC7F95FF9FE51FC5A7F85F0C5C738
- obj.clause-number: 9.7.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-c2a0cdb4967c443: Clause context (obj.clause-number) (provision)
Output for the heading of the clause “1 Scope”:
- obj.clause-heading: “Scope”;
- obj.clause-number: “1”.
- bib.al.original-language: en
- bib.dp.publication-date: 2025-03-01
- ids.document: 100000012
- ids.tracing: hash-793C8010F09621CDC575C217886227AD4A3233EFF386824913D12B3AFE70A5B0
- obj.clause-number: 9.7.2
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-d18794d42dbc43a: Clause context (obj.clause-number) (provision)
EXAMPLE 2:
Output for the element “WARNING: This mixture can be explosively unstable, particularly if heated.” specified within Annex B “Some typical etchants for use at room temperature”:
- obj.clause-heading: “Some typical etchants for use at room temperature”;
- obj.clause-number: “Annex B”.
- bib.al.original-language: en
- bib.dp.publication-date: 2025-03-01
- ids.document: 100000012
- ids.tracing: hash-61E63E009D2F5C826197E8678F2ACF4B7FBA6186A9E944716D5DD020007275F5
- obj.clause-number: 9.7.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> R628

###### prov-100000012-335dbaa83bdf466: Clause context (obj.clause-number) (provision)
Output for the element “WARNING: This mixture can be explosively unstable, particularly if heated.” specified within Annex B “Some typical etchants for use at room temperature”:
- obj.clause-heading: “Some typical etchants for use at room temperature”;
- obj.clause-number: “Annex B”.
- bib.al.original-language: en
- bib.dp.publication-date: 2025-03-01
- ids.document: 100000012
- ids.tracing: hash-285A3CFEDF9C9AAFA4D4702BA6FDD0A1B8C92C0EC568739E35DCEB87D9AC1F15
- obj.clause-number: 9.7.2
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> R628

#### R412: Reliability (obj.conversion-reliability) (heading)
- bib.al.original-language: en
- bib.dp.publication-date: 2025-03-01
- ids.document: 100000012
- obj.clause-number: 9.7.3
- obj.element-name: heading
- obj.language: en
- obj.specobject-type: heading
- ChapterName: 9.7.3 Reliability (obj.conversion-reliability)

##### R413: Determining the reliability (heading)
- bib.al.original-language: en
- bib.dp.publication-date: 2025-03-01
- ids.document: 100000012
- obj.clause-number: 9.7.3.1
- obj.element-name: heading
- obj.language: en
- obj.specobject-type: heading
- ChapterName: 9.7.3.1 Determining the reliability

###### prov-100000012-f4899752a221451: Determining the reliability (provision)
- If the attribute obj.modality (8.2.1.2) has been confirmed by the authority responsible for the public standard, the supplier shall set the obj.conversion-reliability (8.2.1.2) for each SpecObject in the ReqIF™ file to the value “100” (%).
- If the attribute obj.modality (8.2.1.2) has been determined using natural language processing, the supplier may set the attribute obj.conversion-reliability (8.2.1.2) for each SpecObject in the ReqIF™ file to the value between “0” and “99” (%).
- If the attribute obj.modality (8.2.1.2) has not been assessed, the supplier shall not set the attribute obj.conversion-reliability (8.2.1.2) for the respective SpecObjects in the ReqIF™.
- bib.al.original-language: en
- bib.dp.publication-date: 2025-03-01
- ids.document: 100000012
- ids.tracing: hash-66D70200BF00150D43D890E6579C593856087DD29B7857F639A6EDE8440CC992
- obj.clause-number: 9.7.3.1
- obj.element-name: unordered-list
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-100000012-7ba4be86a8a7489: Determining the reliability, list extract (provision)
| → | If the attribute obj.modality (8.2.1.2) has been confirmed by the authority responsible for the public standard, the supplier shall set the obj.conversion-reliability (8.2.1.2) for each SpecObject in the ReqIF™ file to the value “100” (%). |
| --- | --- |
- bib.al.original-language: en
- bib.dp.publication-date: 2025-03-01
- ids.document: 100000012
- ids.tracing: hash-D197B06D5BF6557AF4936BF98639530D86921377602F217562C8D3EAD6AD94DE
- obj.clause-number: 9.7.3.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124

###### prov-100000012-ef0f17e8e6b943d: Determining the reliability, list extract (provision)
| → | If the attribute obj.modality (8.2.1.2) has been determined using natural language processing, the supplier may set the attribute obj.conversion-reliability (8.2.1.2) for each SpecObject in the ReqIF™ file to the value between “0” and “99” (%). |
| --- | --- |
- bib.al.original-language: en
- bib.dp.publication-date: 2025-03-01
- ids.document: 100000012
- ids.tracing: hash-6DE62217EABC92CB8325EE9AF9185562A5ABA8F4BC4BE73E94A6DBE6A941E534
- obj.clause-number: 9.7.3.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124

###### prov-100000012-d1b293a774de42a: Determining the reliability, list extract (provision)
| → | If the attribute obj.modality (8.2.1.2) has not been assessed, the supplier shall not set the attribute obj.conversion-reliability (8.2.1.2) for the respective SpecObjects in the ReqIF™. |
| --- | --- |
- bib.al.original-language: en
- bib.dp.publication-date: 2025-03-01
- ids.document: 100000012
- ids.tracing: hash-7FEE914C23BCD9508980204793328842922E452339FE91371643AD2AB88121F5
- obj.clause-number: 9.7.3.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124

###### prov-100000012-0405415db846403: Determining the reliability (provision)
The users may assume:
- If the attribute obj.conversion-reliability (8.2.1.2) has the value “100”, the supplier expresses that the originator as the authority responsible for the public standard has confirmed the value of the attribute obj.modality (8.2.1.2).
- If the attribute obj.conversion-reliability (8.2.1.2) has the value “0”, the supplier has determined the lowest possible conversion reliability.
- If the attribute obj.conversion-reliability (8.2.1.2) has not been set, the supplier expresses no statement about the conversion reliability.
- bib.al.original-language: en
- bib.dp.publication-date: 2025-03-01
- ids.document: 100000012
- ids.tracing: hash-FE9BE14AC8420D90CFE97B522DD90BE50DDB47E3740E4F159DB65313A96392AE
- obj.clause-number: 9.7.3.1
- obj.element-name: paragraph
- obj.language: en
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124

###### prov-100000012-01c2953878f94cb: Determining the reliability, Note (provision)
NOTE:
Annex D contains typical criteria for the quality of provisions which can be used to determine a value for the attribute obj.conversion-reliability (8.2.1.2).
- bib.al.original-language: en
- bib.dp.publication-date: 2025-03-01
- ids.document: 100000012
- ids.tracing: hash-A728DAB6A7C80BAB91ABBFC820CF0C410125A98E45BC50B89FFAC327E0BEC405
- obj.clause-number: 9.7.3.1
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> R656
- cross-reference -> R124

##### R420: Using the reliability (heading)
- bib.al.original-language: en
- bib.dp.publication-date: 2025-03-01
- ids.document: 100000012
- obj.clause-number: 9.7.3.2
- obj.element-name: heading
- obj.language: en
- obj.specobject-type: heading
- ChapterName: 9.7.3.2 Using the reliability

###### prov-100000012-0eaa5de3457c40a: Using the reliability (provision)
If the attribute obj.conversion-reliability (8.2.1.2) has been set for the respective SpecObject, the users can filter or sort the values to focus or prioritize the review of all SpecObjects in the ReqIF™.
- bib.al.original-language: en
- bib.dp.publication-date: 2025-03-01
- ids.document: 100000012
- ids.tracing: hash-BA97C9527B11946C28D402490C245EF185BCD61E2830E42EB2304E4C51666887
- obj.clause-number: 9.7.3.2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124

###### prov-100000012-3efce5f9bf6940e: Using the reliability (provision)
EXAMPLE:
If all SpecObjects are sorted from the value “0” up to “99” (%), the users can review the SpecObjects beginning with the least estimated reliability up to the highest estimated reliability.
- bib.al.original-language: en
- bib.dp.publication-date: 2025-03-01
- ids.document: 100000012
- ids.tracing: hash-B9717CB1A718303FCE9EB23549244B7323B914A93F33A437C4A3045DFB5586E7
- obj.clause-number: 9.7.3.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-4ee572bf55df483: Using the reliability (provision)
If all SpecObjects are sorted from the value “0” up to “99” (%), the users can review the SpecObjects beginning with the least estimated reliability up to the highest estimated reliability.
- bib.al.original-language: en
- bib.dp.publication-date: 2025-03-01
- ids.document: 100000012
- ids.tracing: hash-CE78D65B13F059A69F6045AD298327BDADE3FDD80D5A42691D45D61A89095F04
- obj.clause-number: 9.7.3.2
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### R424: Standard element (obj.element-name) (heading)
- bib.al.original-language: en
- bib.dp.publication-date: 2025-03-01
- ids.document: 100000012
- obj.clause-number: 9.7.4
- obj.element-name: heading
- obj.language: en
- obj.specobject-type: heading
- ChapterName: 9.7.4 Standard element (obj.element-name)

##### prov-100000012-d27fde245c67493: Standard element (obj.element-name) (provision)
- If the source document is an XML instance, the parent block element shall be output using the corresponding value of the attribute obj.clause-heading (8.2.1.2) according to 9.1.
- If the source document is not an XML instance, the attribute obj.clause-heading (8.2.1.2) shall not be set.
- bib.al.original-language: en
- bib.dp.publication-date: 2025-03-01
- ids.document: 100000012
- ids.tracing: hash-2ABA74B817175B14D78D604D36F6934AB4A022A13BCB3FCC80E64B6916F58615
- obj.clause-number: 9.7.4
- obj.element-name: unordered-list
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-100000012-72bf2617034c4ba: Standard element (obj.element-name), list extract (provision)
| → | If the source document is an XML instance, the parent block element shall be output using the corresponding value of the attribute obj.clause-heading (8.2.1.2) according to 9.1. |
| --- | --- |
- bib.al.original-language: en
- bib.dp.publication-date: 2025-03-01
- ids.document: 100000012
- ids.tracing: hash-366ACDA809A2669683002C08762C3BB7591282D54CAB1CE2D03FFF1DFD2BD675
- obj.clause-number: 9.7.4
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124
- cross-reference -> R206

###### prov-100000012-d3a6da7ef206498: Standard element (obj.element-name), list extract (provision)
| → | If the source document is not an XML instance, the attribute obj.clause-heading (8.2.1.2) shall not be set. |
| --- | --- |
- bib.al.original-language: en
- bib.dp.publication-date: 2025-03-01
- ids.document: 100000012
- ids.tracing: hash-D4CA34C078D54B13D88E754B816F9D9663DD664B48CDBCD44979F2811995A829
- obj.clause-number: 9.7.4
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124

#### R428: Modality (obj.modality) (heading)
- bib.al.original-language: en
- bib.dp.publication-date: 2025-03-01
- ids.document: 100000012
- obj.clause-number: 9.7.5
- obj.element-name: heading
- obj.language: en
- obj.specobject-type: heading
- ChapterName: 9.7.5 Modality (obj.modality)

##### prov-100000012-937d118cf394480: Modality (obj.modality) (provision)
The supplier shall provide the attribute obj.modality (8.2.1.2) for each SpecObject in the ReqIF™ file of a public standard (see 9.5).
- bib.al.original-language: en
- bib.dp.publication-date: 2025-03-01
- ids.document: 100000012
- ids.tracing: hash-F2A8F0874467714D5E210D939CF3A657FE2D0DFBE40448251C2ACF57DC2F6873
- obj.clause-number: 9.7.5
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124
- cross-reference -> R354

#### R430: Language (obj.language) (heading)
- bib.al.original-language: en
- bib.dp.publication-date: 2025-03-01
- ids.document: 100000012
- obj.clause-number: 9.7.6
- obj.element-name: heading
- obj.language: en
- obj.specobject-type: heading
- ChapterName: 9.7.6 Language (obj.language)

##### prov-100000012-b83b4cfd37fd4d5: Language (obj.language) (provision)
The language for the content of the SpecObject shall be set using the corresponding value of the attribute obj.language (8.2.1.2) according to 9.1.
- bib.al.original-language: en
- bib.dp.publication-date: 2025-03-01
- ids.document: 100000012
- ids.tracing: hash-181DE6305B4A564A629392BE5905B64D4E015708E54BEFAF99F314CB39A62B60
- obj.clause-number: 9.7.6
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124
- cross-reference -> R206

##### prov-100000012-99d9de61f1c9489: Language (obj.language) (provision)
If the source document is an XML instance and the language is not specified for the current element, language specified in the metadata of the actual document context may be assumed.
- bib.al.original-language: en
- bib.dp.publication-date: 2025-03-01
- ids.document: 100000012
- ids.tracing: hash-85843626EB6CB1585767C07FE4EBFE5E2CB5F0D9DAE43EA8FC74A1196AEF5278
- obj.clause-number: 9.7.6
- obj.element-name: paragraph
- obj.language: en
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-c0d6cfcc4ebe421: Language (obj.language) (provision)
The list of values for the attribute obj.language (8.2.1.2) has been reduced to focus on the common industrialized countries.
- bib.al.original-language: en
- bib.dp.publication-date: 2025-03-01
- ids.document: 100000012
- ids.tracing: hash-122CC4EF9384ECEF9A28410657BD6B951ACB784AD9A388789C49F0ED9D85AA6D
- obj.clause-number: 9.7.6
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124

#### R434: Normativity (obj.normativity) (heading)
- bib.al.original-language: en
- bib.dp.publication-date: 2025-03-01
- ids.document: 100000012
- obj.clause-number: 9.7.7
- obj.element-name: heading
- obj.language: en
- obj.specobject-type: heading
- ChapterName: 9.7.7 Normativity (obj.normativity)

##### prov-100000012-da9cec693dd74cd: Normativity (obj.normativity) (provision)
The supplier shall set the value of the attribute obj.normativity (8.2.1.2) for each SpecObject in the ReqIF™ file according to Annex C.
- bib.al.original-language: en
- bib.dp.publication-date: 2025-03-01
- ids.document: 100000012
- ids.tracing: hash-3F9106ABE632ECBA1E616754952A6E5AD4C21B2CE5181BC5330DA1A71C353860
- obj.clause-number: 9.7.7
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124
- cross-reference -> R651

#### R436: SpecObject type (obj.specobject-type) (heading)
- bib.al.original-language: en
- bib.dp.publication-date: 2025-03-01
- ids.document: 100000012
- obj.clause-number: 9.7.8
- obj.element-name: heading
- obj.language: en
- obj.specobject-type: heading
- ChapterName: 9.7.8 SpecObject type (obj.specobject-type)

##### prov-100000012-642c06c9af0947f: SpecObject type (obj.specobject-type) (provision)
To increase the interoperability with target systems not supporting different SpecObject types, the supplier shall set the attribute obj.specobject-type (8.2.1.2) for each SpecObject in the ReqIF™ file to:
- “document” if the SpecObject is the title page metadata or the specification of the ReqIF™ file;
- “heading” if the SpecObject is the heading of a provision:
- “provision” if the SpecObject is the content of a provision itself.
- bib.al.original-language: en
- bib.dp.publication-date: 2025-03-01
- ids.document: 100000012
- ids.tracing: hash-E1B5DDD7A40380EAADC750F7E03C528F162710D249C6B1B990374F70A51552FF
- obj.clause-number: 9.7.8
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124

###### prov-100000012-e09237a436cd480: SpecObject type (obj.specobject-type), Note (provision)
NOTE:
Table 25 illustrates the settings of values for the listed attributes depending on the usage of either 3 different or one SpecObjectType depending on the support or lack of support in the target software.
- bib.al.original-language: en
- bib.dp.publication-date: 2025-03-01
- ids.document: 100000012
- ids.tracing: hash-6CFAEFF0D8D3141029700C08538AF4FE3D97C064CBE5375B27760ACB0664EB45
- obj.clause-number: 9.7.8
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-100000012-0b32a88c139341e

##### prov-100000012-0b32a88c139341e: Setting of values depending on the SpecObjectType (provision)
Table 25 — Setting of values depending on the SpecObjectType
| attribute name | 3 SpecObjectType |  |  | 1 SpecObjectType |
| --- | --- | --- | --- | --- |
| attribute name | document | heading | provision | provision |
| ReqIF.ChapterName | no | yes | no | yes |
| ReqIF.Text | yes | no | yes | yes |
| obj.clause-heading | no | yes | yes | yes |
| obj.clause-number | no | yes | yes | yes |
| obj.specobject-type | document | heading | provision | document, heading, or provision |
- bib.al.original-language: en
- bib.dp.publication-date: 2025-03-01
- ids.document: 100000012
- ids.tracing: hash-9CFDF28E246E6FEC9F7CFE72A5277DA5AEEF7519F7EB796F8A7FBA37AF366DD3
- obj.clause-number: Table 25
- obj.element-name: table
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### R440: Conversion issues (obj.transformation-issues) (heading)
- bib.al.original-language: en
- bib.dp.publication-date: 2025-03-01
- ids.document: 100000012
- obj.clause-number: 9.7.9
- obj.element-name: heading
- obj.language: en
- obj.specobject-type: heading
- ChapterName: 9.7.9 Conversion issues (obj.transformation-issues)

##### prov-100000012-7fd142c2cbf5440: Conversion issues (obj.transformation-issues) (provision)
If the source document is an XML instance, the supplier can support the users review with additional information as values of the attribute obj.transformation-issues (8.2.1.2).
- bib.al.original-language: en
- bib.dp.publication-date: 2025-03-01
- ids.document: 100000012
- ids.tracing: hash-EDEF6E81B9ABCBE34F1768106F34B12368474B516F7FA9EDBD1CAB95B7C6124D
- obj.clause-number: 9.7.9
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124

##### prov-100000012-0c2ae58e02bd447: Conversion issues (obj.transformation-issues) (provision)
If the attribute obj.transformation-issues (8.2.1.2) has been set for the respective SpecObject, the users can filter or sort the values to focus or prioritize the review of all SpecObjects in the ReqIF™.
- bib.al.original-language: en
- bib.dp.publication-date: 2025-03-01
- ids.document: 100000012
- ids.tracing: hash-742BBAE30CDF5B37F3EB4E169FB3E6F026428ECB858D83763BC3892CF88B51F3
- obj.clause-number: 9.7.9
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124

### R443: Use attributes for intra-company management (use.*) (heading)
- bib.al.original-language: en
- bib.dp.publication-date: 2025-03-01
- ids.document: 100000012
- obj.clause-number: 9.8
- obj.element-name: heading
- obj.language: en
- obj.specobject-type: heading
- ChapterName: 9.8 Use attributes for intra-company management (use.*)

#### R444: Business process (use.business-process) (heading)
- bib.al.original-language: en
- bib.dp.publication-date: 2025-03-01
- ids.document: 100000012
- obj.clause-number: 9.8.1
- obj.element-name: heading
- obj.language: en
- obj.specobject-type: heading
- ChapterName: 9.8.1 Business process (use.business-process)

##### prov-100000012-0053b63a56f94c6: Business process (use.business-process) (provision)
The users can assign one or more values for the applicable business process where the provision is relevant.
- bib.al.original-language: en
- bib.dp.publication-date: 2025-03-01
- ids.document: 100000012
- ids.tracing: hash-8A55DC18DAC10F5681AC568E88B6F5523199989AA69E9907688A19AC4FDF6BC3
- obj.clause-number: 9.8.1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-9857f8f5e8774f8: Business process (use.business-process) (provision)
To achieve interoperability between different companies, the list of values for the attribute use.business-process (8.2.1.3) has been generalized to Porter [9] plus the usual supporting processes.
- bib.al.original-language: en
- bib.dp.publication-date: 2025-03-01
- ids.document: 100000012
- ids.tracing: hash-2FE7351D272B9F7796ECABC56E86CAF0A836F019E88520EEC9FE612FEC759361
- obj.clause-number: 9.8.1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R127
- cross-reference -> prov-100000012-996957e8ccc24fe

##### prov-100000012-1bbe47bbdbd544e: Business process (use.business-process) (provision)
EXAMPLE:
“production; supporting – technology development” if the requirement is relevant for the production and for the development of a product or part, e. g., a valve nozzle.
- bib.al.original-language: en
- bib.dp.publication-date: 2025-03-01
- ids.document: 100000012
- ids.tracing: hash-C6469588691773DCCDCDBE09D79E163E298C68AEDDA80F8F07ED42D23411641B
- obj.clause-number: 9.8.1
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-b8f2ee9d9157476: Business process (use.business-process) (provision)
“production; supporting – technology development” if the requirement is relevant for the production and for the development of a product or part, e. g., a valve nozzle.
- bib.al.original-language: en
- bib.dp.publication-date: 2025-03-01
- ids.document: 100000012
- ids.tracing: hash-29991331447627DB50F7ED29B911E35A7800F18E7ABED0D305BAD9757684BD1B
- obj.clause-number: 9.8.1
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### R449: Business sector; industry sector (use.business-sector) (heading)
- bib.al.original-language: en
- bib.dp.publication-date: 2025-03-01
- ids.document: 100000012
- obj.clause-number: 9.8.2
- obj.element-name: heading
- obj.language: en
- obj.specobject-type: heading
- ChapterName: 9.8.2 Business sector; industry sector (use.business-sector)

##### prov-100000012-eebac23eceba42f: Business sector; industry sector (use.business-sector) (provision)
The users can assign one or more values for the applicable business sector where the provision is relevant.
- bib.al.original-language: en
- bib.dp.publication-date: 2025-03-01
- ids.document: 100000012
- ids.tracing: hash-25D3B08C9F4B12C046A6576A90D8AF8A6DC965E97FD2C29C020E72633CBAE1AF
- obj.clause-number: 9.8.2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-735aec2c7d47479: Business sector; industry sector (use.business-sector) (provision)
EXAMPLE:
“industrials – mechanical engineering” if the requirement is relevant for the mechanical engineering parts of a system, e. g., a printing-on-demand line.
- bib.al.original-language: en
- bib.dp.publication-date: 2025-03-01
- ids.document: 100000012
- ids.tracing: hash-1D52EEA3E2C75F68B8D60CD91B7F26446055B978FB4AA22BA02D3EB8D91F6F32
- obj.clause-number: 9.8.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-9bd9ca67d7a941e: Business sector; industry sector (use.business-sector) (provision)
“industrials – mechanical engineering” if the requirement is relevant for the mechanical engineering parts of a system, e. g., a printing-on-demand line.
- bib.al.original-language: en
- bib.dp.publication-date: 2025-03-01
- ids.document: 100000012
- ids.tracing: hash-F7BF5325B2DC615A36EE401863AFBCF8F9D23E48B0F721AF39DE76FBC8566AAE
- obj.clause-number: 9.8.2
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### R453: Date usage begins (use.date-usage-begins) (heading)
- bib.al.original-language: en
- bib.dp.publication-date: 2025-03-01
- ids.document: 100000012
- obj.clause-number: 9.8.3
- obj.element-name: heading
- obj.language: en
- obj.specobject-type: heading
- ChapterName: 9.8.3 Date usage begins (use.date-usage-begins)

##### prov-100000012-5b999de8088c454: Date usage begins (use.date-usage-begins) (provision)
The users can assign one or more values for the applicable date when implementation of the provision is going to begin, expressed in the format YYYY-MM-DD according to DIN ISO 8601-1.
- bib.al.original-language: en
- bib.dp.publication-date: 2025-03-01
- ids.document: 100000012
- ids.tracing: hash-475A91F315E9B4A1784544705F33B15CE6B1B6D7B28E2690CB77B43F8ECED986
- obj.clause-number: 9.8.3
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-32d1605c51884f0: Date usage begins (use.date-usage-begins) (provision)
EXAMPLE:
“2024-01-01” if this is date to begin the implementation of a requirement from the new medical device directive.
- bib.al.original-language: en
- bib.dp.publication-date: 2025-03-01
- ids.document: 100000012
- ids.tracing: hash-05701ADFD273A855549DBC61886F031657282324B8191A7097C7D87D9989A734
- obj.clause-number: 9.8.3
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-ad2b6d7421a74fd: Date usage begins (use.date-usage-begins) (provision)
“2024-01-01” if this is date to begin the implementation of a requirement from the new medical device directive.
- bib.al.original-language: en
- bib.dp.publication-date: 2025-03-01
- ids.document: 100000012
- ids.tracing: hash-C0257321B6173347039EAFE49631769E60A676A7C5218C1C69D854FF51960DC6
- obj.clause-number: 9.8.3
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### R457: Date usage ends (use.date-usage-ends) (heading)
- bib.al.original-language: en
- bib.dp.publication-date: 2025-03-01
- ids.document: 100000012
- obj.clause-number: 9.8.4
- obj.element-name: heading
- obj.language: en
- obj.specobject-type: heading
- ChapterName: 9.8.4 Date usage ends (use.date-usage-ends)

##### prov-100000012-db38a09d29b7487: Date usage ends (use.date-usage-ends) (provision)
The users can assign zero or one values for the applicable date when implementation of the provision may terminate, expressed in the format YYYY-MM-DD according to DIN ISO 8601-1.
- bib.al.original-language: en
- bib.dp.publication-date: 2025-03-01
- ids.document: 100000012
- ids.tracing: hash-D8774A26DA55B176524D965FB64C511C4FCC0F7C72260FBC0FC1DD1BD54DF6C6
- obj.clause-number: 9.8.4
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-689fd2286e244dd: Date usage ends (use.date-usage-ends) (provision)
EXAMPLE:
“2027-12-31” if this is date to end the implementation of a requirement from the new medical device directive.
- bib.al.original-language: en
- bib.dp.publication-date: 2025-03-01
- ids.document: 100000012
- ids.tracing: hash-D2E0691B435D976F32DC6D6340FC719E5E8D448FF7CFD42ADAD784A7C7709EA8
- obj.clause-number: 9.8.4
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-e0258634033747c: Date usage ends (use.date-usage-ends) (provision)
“2027-12-31” if this is date to end the implementation of a requirement from the new medical device directive.
- bib.al.original-language: en
- bib.dp.publication-date: 2025-03-01
- ids.document: 100000012
- ids.tracing: hash-6F5AD9EABB363127528FA4C4D21416F98045558AD8B126B1D755B9C25D2D45AA
- obj.clause-number: 9.8.4
- obj.element-name: paragraph
- obj.language: en
- obj.modality: requirement
- obj.normativity: informative
- obj.specobject-type: provision
- use.business-process: undefined
- use.business-sector: undefined
- use.interaction: undefined
- use.location: undefined
- use.product-category: undefined
- use.product-life-cycle: undefined
- use.project-phase: undefined
- use.purpose: undefined

#### R461: Interaction (use.interaction) (heading)
- bib.al.original-language: en
- bib.dp.publication-date: 2025-03-01
- ids.document: 100000012
- obj.clause-number: 9.8.5
- obj.element-name: heading
- obj.language: en
- obj.specobject-type: heading
- ChapterName: 9.8.5 Interaction (use.interaction)

##### prov-100000012-70992b6d281046c: Interaction (use.interaction) (provision)
The users can assign one or more values for a type of interaction of the provision.
- bib.al.original-language: en
- bib.dp.publication-date: 2025-03-01
- ids.document: 100000012
- ids.tracing: hash-BFD60B95FFE1273ABC8291484AB6A094A8928D0D1493168ACE724B0208891EE5
- obj.clause-number: 9.8.5
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-6f2c712b3aae493: Interaction (use.interaction) (provision)
EXAMPLE:
“integral aspect” if the requirement serves an integral aspect of a system, e. g., a railway network.
- bib.al.original-language: en
- bib.dp.publication-date: 2025-03-01
- ids.document: 100000012
- ids.tracing: hash-6C990FB488E90BFD0EF7795DAAA593AB8046692DB1F47D13E1BA03947981B58F
- obj.clause-number: 9.8.5
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-5fae52f1ad0448f: Interaction (use.interaction) (provision)
“integral aspect” if the requirement serves an integral aspect of a system, e. g., a railway network.
- bib.al.original-language: en
- bib.dp.publication-date: 2025-03-01
- ids.document: 100000012
- ids.tracing: hash-32BF4A9667CA6D607A6E6C54FB06E32D060DED9EE51AC46A446AE81AD9D7C42C
- obj.clause-number: 9.8.5
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### R465: Implementation region (use.location) (heading)
- bib.al.original-language: en
- bib.dp.publication-date: 2025-03-01
- ids.document: 100000012
- obj.clause-number: 9.8.6
- obj.element-name: heading
- obj.language: en
- obj.specobject-type: heading
- ChapterName: 9.8.6 Implementation region (use.location)

##### prov-100000012-925c2cf327604e3: Implementation region (use.location) (provision)
The users can assign one or more values for the geological locations where the provision is going to be implemented, expressed as lower-case ALPHA-3 country code according to DIN EN ISO 3166-1.
- bib.al.original-language: en
- bib.dp.publication-date: 2025-03-01
- ids.document: 100000012
- ids.tracing: hash-544B422142A64122150C72CA364535F74F42A9321299CB6A9C00FF67133E3038
- obj.clause-number: 9.8.6
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-077924bce8d94ba: Implementation region (use.location) (provision)
The list of values for the attribute use.location (8.2.1.3) has been reduced to focus on common industrialized and producing countries.
- bib.al.original-language: en
- bib.dp.publication-date: 2025-03-01
- ids.document: 100000012
- ids.tracing: hash-F375E91C85D1347EE5DDFFA0C3F1E031202C126D85BC2945E52134FF04A39A5C
- obj.clause-number: 9.8.6
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R127

##### prov-100000012-1ddf58ae2267452: Implementation region (use.location) (provision)
The list of values for the attribute use.location (8.2.1.3) has been extended with additional codes to support continents and some regionally common locations.
- bib.al.original-language: en
- bib.dp.publication-date: 2025-03-01
- ids.document: 100000012
- ids.tracing: hash-A87B71D825E9E2F79E8CD9F9AEA306CC71002FEDB713B314CFFB1F76B5E6E048
- obj.clause-number: 9.8.6
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R127

##### prov-100000012-9ff783714d9e4c5: Implementation region (use.location) (provision)
EXAMPLE:
“eee; usa” if Europe and the United States of America are the regions where the requirement is going to be implemented, e. g., legislative regulations for the handling of person-related data within social media software.
- bib.al.original-language: en
- bib.dp.publication-date: 2025-03-01
- ids.document: 100000012
- ids.tracing: hash-BAE3E991107102AF87F22C0950EBD49CE272308A8ED5607998EA24018871350F
- obj.clause-number: 9.8.6
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-97eb8a3bc4e9407: Implementation region (use.location) (provision)
“eee; usa” if Europe and the United States of America are the regions where the requirement is going to be implemented, e. g., legislative regulations for the handling of person-related data within social media software.
- bib.al.original-language: en
- bib.dp.publication-date: 2025-03-01
- ids.document: 100000012
- ids.tracing: hash-94925F4E5E6E3AB2DDE641B64773EFE1F94ED038B479B2FA27832DF24D043DB0
- obj.clause-number: 9.8.6
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### R471: Project phase (use.project-phase) (heading)
- bib.al.original-language: en
- bib.dp.publication-date: 2025-03-01
- ids.document: 100000012
- obj.clause-number: 9.8.7
- obj.element-name: heading
- obj.language: en
- obj.specobject-type: heading
- ChapterName: 9.8.7 Project phase (use.project-phase)

##### prov-100000012-c3c3a622396a46f: Project phase (use.project-phase) (provision)
The users can assign one or more values for the applicable project phase where the provision is relevant.
- bib.al.original-language: en
- bib.dp.publication-date: 2025-03-01
- ids.document: 100000012
- ids.tracing: hash-9F21FB138E944C62E51C94E2139562E03182981CE82C9BC458D8C499B03BE62D
- obj.clause-number: 9.8.7
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-1e37da0c05c146b: Project phase (use.project-phase) (provision)
EXAMPLE:
“definition and planning; execution” if the recommendation is relevant for the specification phase and the and realization phase of a project, e. g., the development of the firmware for a control unit.
- bib.al.original-language: en
- bib.dp.publication-date: 2025-03-01
- ids.document: 100000012
- ids.tracing: hash-88378C98972DFE7E5FFAD006FFC969976821BDB02F8875179A5D8CC1F277ECB9
- obj.clause-number: 9.8.7
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-04a25219f08e479: Project phase (use.project-phase) (provision)
“definition and planning; execution” if the recommendation is relevant for the specification phase and the and realization phase of a project, e. g., the development of the firmware for a control unit.
- bib.al.original-language: en
- bib.dp.publication-date: 2025-03-01
- ids.document: 100000012
- ids.tracing: hash-2CBB32087DA757AEF3C2BC36F902825B66E0C38FF6A670B9CDD03D964CC1761B
- obj.clause-number: 9.8.7
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### R475: Product category (use.product-category) (heading)
- bib.al.original-language: en
- bib.dp.publication-date: 2025-03-01
- ids.document: 100000012
- obj.clause-number: 9.8.8
- obj.element-name: heading
- obj.language: en
- obj.specobject-type: heading
- ChapterName: 9.8.8 Product category (use.product-category)

##### prov-100000012-3b65c7c60d7f45e: Product category (use.product-category) (provision)
The users can assign one or more values for the applicable product category where the provision is relevant.
- bib.al.original-language: en
- bib.dp.publication-date: 2025-03-01
- ids.document: 100000012
- ids.tracing: hash-8D6A27F531115A13FEDE7A40F4914ECDD3FE4F13C7B4FA974DCC4AB7771821B1
- obj.clause-number: 9.8.8
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-57c6203e34d14d4: Product category (use.product-category) (provision)
If the product category is used, the stakeholder relevant for the interoperability context should align on harmonized product categories.
- bib.al.original-language: en
- bib.dp.publication-date: 2025-03-01
- ids.document: 100000012
- ids.tracing: hash-03C055EC6B2BCA62F6D63C56019601FDEF82DDE8A080130CAD8F3EDB1AC1ABF3
- obj.clause-number: 9.8.8
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-e5b347fb6fce432: Product category (use.product-category) (provision)
EXAMPLE:
“roller bearings” if the recommendation is relevant for this part of, e. g., an automobile.
- bib.al.original-language: en
- bib.dp.publication-date: 2025-03-01
- ids.document: 100000012
- ids.tracing: hash-88E93E0830FEC505CECD9D093F01C7A379D7200EBD403370EB94A77D347F7614
- obj.clause-number: 9.8.8
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-8ddd1b859aee46b: Product category (use.product-category) (provision)
“roller bearings” if the recommendation is relevant for this part of, e. g., an automobile.
- bib.al.original-language: en
- bib.dp.publication-date: 2025-03-01
- ids.document: 100000012
- ids.tracing: hash-856C665E4F48A6266E51FCB30EDC481EE125A3E412DC2A4097336162F7B761FF
- obj.clause-number: 9.8.8
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### R480: Product life cycle (use.product-life-cycle) (heading)
- bib.al.original-language: en
- bib.dp.publication-date: 2025-03-01
- ids.document: 100000012
- obj.clause-number: 9.8.9
- obj.element-name: heading
- obj.language: en
- obj.specobject-type: heading
- ChapterName: 9.8.9 Product life cycle (use.product-life-cycle)

##### prov-100000012-59cf7e0b461844f: Product life cycle (use.product-life-cycle) (provision)
The users can assign one or more values for the applicable phase in the life cycle of a product where the provision is relevant, typically for managing the provision within a product lifecycle management (PLM) process.
- bib.al.original-language: en
- bib.dp.publication-date: 2025-03-01
- ids.document: 100000012
- ids.tracing: hash-BB23DC96E77C8E37A9B359DCDB5F189EB73BE5213DB64BD88DC6D307DA24437B
- obj.clause-number: 9.8.9
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-f38967e9dcb64aa: Product life cycle (use.product-life-cycle) (provision)
EXAMPLE:
“design; recycling” if the requirement is relevant for the design of a product or for the disposal or the recycling of a product, e. g., a lithium battery.
- bib.al.original-language: en
- bib.dp.publication-date: 2025-03-01
- ids.document: 100000012
- ids.tracing: hash-01A32CAE032D5F392015C17C1F429B862FA54704DC726040E9F0EA1E07D8CECE
- obj.clause-number: 9.8.9
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-eb3c967b8db3456: Product life cycle (use.product-life-cycle) (provision)
“design; recycling” if the requirement is relevant for the design of a product or for the disposal or the recycling of a product, e. g., a lithium battery.
- bib.al.original-language: en
- bib.dp.publication-date: 2025-03-01
- ids.document: 100000012
- ids.tracing: hash-B273A4517CC100AB3CF2AEF78C0B1D516530A9FB27327E8888521B2296BB8B2E
- obj.clause-number: 9.8.9
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### R484: Purpose; intention; focus (use.purpose) (heading)
- bib.al.original-language: en
- bib.dp.publication-date: 2025-03-01
- ids.document: 100000012
- obj.clause-number: 9.8.10
- obj.element-name: heading
- obj.language: en
- obj.specobject-type: heading
- ChapterName: 9.8.10 Purpose; intention; focus (use.purpose)

##### prov-100000012-664ea1318cfb4cb: Purpose; intention; focus (use.purpose) (provision)
The users can assign one or more values for primary scope of the provision.
- bib.al.original-language: en
- bib.dp.publication-date: 2025-03-01
- ids.document: 100000012
- ids.tracing: hash-7D2A8746DDC86278D6BD3293D40FF70950910F9B928ACEC43E89A19971AD525C
- obj.clause-number: 9.8.10
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-87a3b43c4cda4df: Purpose; intention; focus (use.purpose) (provision)
EXAMPLE:
“safety” if the requirement serves to achieve safety, e. g., an emergency stop switch.
- bib.al.original-language: en
- bib.dp.publication-date: 2025-03-01
- ids.document: 100000012
- ids.tracing: hash-16E8AC021CF3AC530ACF08234E9F085F8F0998BA4BDDF1D71ADFD1D8B5999141
- obj.clause-number: 9.8.10
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-055063e296ee4bd: Purpose; intention; focus (use.purpose) (provision)
“safety” if the requirement serves to achieve safety, e. g., an emergency stop switch.
- bib.al.original-language: en
- bib.dp.publication-date: 2025-03-01
- ids.document: 100000012
- ids.tracing: hash-FF334D3BC21FDA7A35B487FD7C2E8D5F4DF67C1C237151F0D9B33CA065F14B60
- obj.clause-number: 9.8.10
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### R488: Bibliographic document metadata (bib.*) (heading)
- bib.al.original-language: en
- bib.dp.publication-date: 2025-03-01
- ids.document: 100000012
- obj.clause-number: 9.9
- obj.element-name: heading
- obj.language: en
- obj.specobject-type: heading
- ChapterName: 9.9 Bibliographic document metadata (bib.*)

#### prov-100000012-86a2a8e624a34c6: Bibliographic document metadata (bib.*) (provision)
The supplier shall interpret the output for the bibliographic document metadata (see 8.2.1.4) according to the Metadata Field Specification.
- bib.al.original-language: en
- bib.dp.publication-date: 2025-03-01
- ids.document: 100000012
- ids.tracing: hash-4819225BFBA9DCFF3C3519B5EEFD5FE4F5940243618E7311555E8DB4F1C9869F
- obj.clause-number: 9.9
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R130

#### prov-100000012-ea7f0a2bd210496: Bibliographic document metadata (bib.*) (provision)
For the International Classification System (ICS), the supplier shall set the value of the attribute bib.ca.classification (8.2.1.4) according to ISO specification, using “ICS”, the number, and the description concatenated.
- bib.al.original-language: en
- bib.dp.publication-date: 2025-03-01
- ids.document: 100000012
- ids.tracing: hash-60DEAF589D48CC57E09A45E31675EB9128929B381F63C5D47D1FB98A65903B3E
- obj.clause-number: 9.9
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R130

### R491: Identifier (ID) attributes (ids.*) (heading)
- bib.al.original-language: en
- bib.dp.publication-date: 2025-03-01
- ids.document: 100000012
- obj.clause-number: 9.10
- obj.element-name: heading
- obj.language: en
- obj.specobject-type: heading
- ChapterName: 9.10 Identifier (ID) attributes (ids.*)

#### R492: Document ID (heading)
- bib.al.original-language: en
- bib.dp.publication-date: 2025-03-01
- ids.document: 100000012
- obj.clause-number: 9.10.1
- obj.element-name: heading
- obj.language: en
- obj.specobject-type: heading
- ChapterName: 9.10.1 Document ID

##### prov-100000012-21404188d17e4b0: Document ID (provision)
If provided, the document ID shall be unique for same version of the same document.
- bib.al.original-language: en
- bib.dp.publication-date: 2025-03-01
- ids.document: 100000012
- ids.tracing: hash-65DBA70D86F8BF13E718064BE6CAFC300B091CF672922ED14DA9BF810526560D
- obj.clause-number: 9.10.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-b6a86fe0f9054a6: Document ID (provision)
The document ID can be used to identify documents uniquely across all documents in the target software.
- bib.al.original-language: en
- bib.dp.publication-date: 2025-03-01
- ids.document: 100000012
- ids.tracing: hash-C23F4A03C7E3D3D9A2C9B739F79F1B4D2188F6D933D7E51A294C59CFA0FB92EE
- obj.clause-number: 9.10.1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-628b202904a646e: Document ID (provision)
The supplier shall provide a document ID as value of the attribute ids.document (8.2.1.5) for each SpecObject in the ReqIF™ file.
- bib.al.original-language: en
- bib.dp.publication-date: 2025-03-01
- ids.document: 100000012
- ids.tracing: hash-596AFE212B4D6D843A28EB5C1AA4953CC6AB5CF2FDD5CCD9FF73DDEDD1D8BBD9
- obj.clause-number: 9.10.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R134

##### prov-100000012-4d1c9db516254b8: Document ID (provision)
The method for determining values for the document ID may follow the best-practice identified by the stakeholders relevant for the interoperability context.
- bib.al.original-language: en
- bib.dp.publication-date: 2025-03-01
- ids.document: 100000012
- ids.tracing: hash-AB29AB92D510DEC346144C7448CC940AA7CD23D0F1395093212E487D02BCC605
- obj.clause-number: 9.10.1
- obj.element-name: paragraph
- obj.language: en
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

#### R497: Element ID (heading)
- bib.al.original-language: en
- bib.dp.publication-date: 2025-03-01
- ids.document: 100000012
- obj.clause-number: 9.10.2
- obj.element-name: heading
- obj.language: en
- obj.specobject-type: heading
- ChapterName: 9.10.2 Element ID

##### prov-100000012-627ac190848145f: Element ID (provision)
If provided, the element ID shall be unique for the same fragment within the same version of the same document.
- bib.al.original-language: en
- bib.dp.publication-date: 2025-03-01
- ids.document: 100000012
- ids.tracing: hash-11DEC8CD4FF1E7B3A554D9D3BB352EDEA7E4F6E55653144A8D819E504562EE5C
- obj.clause-number: 9.10.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-2b44c40bd1674ec: Element ID (provision)
The element ID can be used to link to fragments within target documents even if they are currently not accessible, using speaking identifiers (IDs) based on the references within the source document.
- bib.al.original-language: en
- bib.dp.publication-date: 2025-03-01
- ids.document: 100000012
- ids.tracing: hash-68274FAA4CB1D26AA96AEC91B7B2C4895B6261606D500F8E5F7EAA900D247DFF
- obj.clause-number: 9.10.2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-859e283efee9413: Element ID (provision)
If the source document is an XML instance, the supplier shall provide an element ID as value of the attribute ids.element (8.2.1.5) for each SpecObject in the ReqIF™ file.
- bib.al.original-language: en
- bib.dp.publication-date: 2025-03-01
- ids.document: 100000012
- ids.tracing: hash-42C17D6BFAE6E7C3B88C9DF0E530BF7826A9B02F44A2BB7E9E496FDF58540BE6
- obj.clause-number: 9.10.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R134

##### prov-100000012-92d69d61e2744b1: Element ID (provision)
The method for determining values for the element ID may follow the best-practice identified by the stakeholders relevant for the interoperability context.
- bib.al.original-language: en
- bib.dp.publication-date: 2025-03-01
- ids.document: 100000012
- ids.tracing: hash-9F7CFEA45F912802F7C5EE647103A3F0A422DE1B746E6CA4EAC6643D50F6A391
- obj.clause-number: 9.10.2
- obj.element-name: paragraph
- obj.language: en
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

#### R502: Language-independent ID (heading)
- bib.al.original-language: en
- bib.dp.publication-date: 2025-03-01
- ids.document: 100000012
- obj.clause-number: 9.10.3
- obj.element-name: heading
- obj.language: en
- obj.specobject-type: heading
- ChapterName: 9.10.3 Language-independent ID

##### prov-100000012-b38addf8e879433: Language-independent ID (provision)
If provided, the language-independent ID shall be unique for the same fragment across all language variants within the same version of the same document.
- bib.al.original-language: en
- bib.dp.publication-date: 2025-03-01
- ids.document: 100000012
- ids.tracing: hash-62D16D9458763634CAB1F718C2299C6E69F277AEB6ED7F948A1B381192D813A1
- obj.clause-number: 9.10.3
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-21147f90294a48d: Language-independent ID (provision)
The language-independent ID can be used to identify the synoptic fragments across all language variants within the same version of the same document.
- bib.al.original-language: en
- bib.dp.publication-date: 2025-03-01
- ids.document: 100000012
- ids.tracing: hash-2E7129D7E3ED9474B4B25DDE3853AB9AB4122D850E205EB73DA892B3BBF83431
- obj.clause-number: 9.10.3
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-f76d307834db4d4: Language-independent ID (provision)
If the value of the element ID (see 9.10.2) is set to a language-dependent value, the supplier should provide the attribute ids.language-synoptic (8.2.1.5) with a language-independent value for the SpecObject.
- bib.al.original-language: en
- bib.dp.publication-date: 2025-03-01
- ids.document: 100000012
- ids.tracing: hash-820F7FC2D5BBBA175049036F60838DA76E3082E4E4BBB280A69DBD91509D1311
- obj.clause-number: 9.10.3
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R497
- cross-reference -> R134

##### prov-100000012-580141e3f4c14d8: Language-independent ID (provision)
The method for determining values for the language-independent ID may follow the best-practice identified by the stakeholders relevant for the interoperability context.
- bib.al.original-language: en
- bib.dp.publication-date: 2025-03-01
- ids.document: 100000012
- ids.tracing: hash-2DC7B96619DE8F8854FCC4F5C10600A9C726B93FAB25BBAB67147792A2787CDC
- obj.clause-number: 9.10.3
- obj.element-name: paragraph
- obj.language: en
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

#### R507: Path-IDs (heading)
- bib.al.original-language: en
- bib.dp.publication-date: 2025-03-01
- ids.document: 100000012
- obj.clause-number: 9.10.4
- obj.element-name: heading
- obj.language: en
- obj.specobject-type: heading
- ChapterName: 9.10.4 Path-IDs

##### prov-100000012-81c2661f9b70421: Path-IDs (provision)
If provided, the path IDs shall enable marking the start and the end of a fragment within the source document.
- bib.al.original-language: en
- bib.dp.publication-date: 2025-03-01
- ids.document: 100000012
- ids.tracing: hash-F292527F3A4683C44D92865BE241C6EF9252620A025A3847D08FCF96CB04AA58
- obj.clause-number: 9.10.4
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-56be21c8861d449: Path-IDs (provision)
The path IDs can be used to access fragments uniquely by using path and offset independently or below the element contexts given in the content.
- bib.al.original-language: en
- bib.dp.publication-date: 2025-03-01
- ids.document: 100000012
- ids.tracing: hash-657F5C27553A7CE1843D0AA449B5E823FED49C308FB19E0918A7A0D6E9FFB098
- obj.clause-number: 9.10.4
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-fb9bad4cd12a493: Path-IDs (provision)
If the source document is an XML instance, the supplier should provide path IDs for each SpecObject in the ReqIF™ file in the form of the XPath:
- to the start of the SpecObject as value of the attribute ids.xpath-start (8.2.1.5);
- to the end of the SpecObject as value of the attribute ids.xpath-end (8.2.1.5);
- bib.al.original-language: en
- bib.dp.publication-date: 2025-03-01
- ids.document: 100000012
- ids.tracing: hash-E1E68ED01DAD19BDB9B3F22E36906776A4B21B22FED4432C374652D1161CC9CF
- obj.clause-number: 9.10.4
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R134

##### prov-100000012-14e9bf89aa2344b: Path-IDs (provision)
If the source document is not an XML instance, the attributes shall be omitted.
- bib.al.original-language: en
- bib.dp.publication-date: 2025-03-01
- ids.document: 100000012
- ids.tracing: hash-B9C022B47574FBF4D142012560E09CA929C9D6656A9746C11FADF8E26EB9509C
- obj.clause-number: 9.10.4
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-0f435b1d306447c: Path-IDs (provision)
The method for determining values for the path IDs may follow the best-practice identified by the stakeholders relevant for the interoperability context.
- bib.al.original-language: en
- bib.dp.publication-date: 2025-03-01
- ids.document: 100000012
- ids.tracing: hash-00764F6BB9D0154EFC5071F26CE0D0FC45D0E0B8E7DFBD4650D14C37FF5CD3BB
- obj.clause-number: 9.10.4
- obj.element-name: paragraph
- obj.language: en
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

#### R513: Version-independent tracing ID (heading)
- bib.al.original-language: en
- bib.dp.publication-date: 2025-03-01
- ids.document: 100000012
- obj.clause-number: 9.10.5
- obj.element-name: heading
- obj.language: en
- obj.specobject-type: heading
- ChapterName: 9.10.5 Version-independent tracing ID

##### prov-100000012-3833a943fa9e4c9: Version-independent tracing ID (provision)
If provided, the tracing ID shall be unique for the same content of the same fragment across all versions of the same document.
- bib.al.original-language: en
- bib.dp.publication-date: 2025-03-01
- ids.document: 100000012
- ids.tracing: hash-8DDD7D5F631C4D223D65E246F0B2A2ECBD237A0AAE7FC77B656E64B002F612B8
- obj.clause-number: 9.10.5
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-508c8f5fa5e844c: Version-independent tracing ID (provision)
The tracing ID can be used to identify content of the provision that is unique within a certain clause across multiple editions of the same standard.
- bib.al.original-language: en
- bib.dp.publication-date: 2025-03-01
- ids.document: 100000012
- ids.tracing: hash-F978AC35A45193A98A33C22F8B07C2C9E210A7F15FF41B49E57B28D7127A7884
- obj.clause-number: 9.10.5
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-ea163517654c4c4: Version-independent tracing ID (provision)
The supplier should provide a tracing ID as value of the attribute ids.tracing (8.2.1.5) for each SpecObject in the ReqIF™ file.
- bib.al.original-language: en
- bib.dp.publication-date: 2025-03-01
- ids.document: 100000012
- ids.tracing: hash-BDFE7E31E398A352524B1713FD0725E7FDE2FCCCBD9280CE028CE109C64B2267
- obj.clause-number: 9.10.5
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R134

##### prov-100000012-4b32757b433141f: Version-independent tracing ID (provision)
The method for determining values for the tracing ID may follow the best-practice identified by the stakeholders relevant for the interoperability context.
- bib.al.original-language: en
- bib.dp.publication-date: 2025-03-01
- ids.document: 100000012
- ids.tracing: hash-7000BB327FCB67FAD95B1A6235BC4D45014824AFE6ECD05537239874E5A0D175
- obj.clause-number: 9.10.5
- obj.element-name: paragraph
- obj.language: en
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-0a0e908a145e426: Version-independent tracing ID (provision)
A tracing ID and a unique ID shall be differentiated since one and the same ID cannot be the same over all versions of the same SpecObject as well as uniquely different over all versions of all SpecObjects (see 9.10.6).
- bib.al.original-language: en
- bib.dp.publication-date: 2025-03-01
- ids.document: 100000012
- ids.tracing: hash-0BE0BAF050C1853626B7C2D9F93DA9002E2AFEAA59975EB742220308133427AA
- obj.clause-number: 9.10.5
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R519

#### R519: Version-dependent unique ID (heading)
- bib.al.original-language: en
- bib.dp.publication-date: 2025-03-01
- ids.document: 100000012
- obj.clause-number: 9.10.6
- obj.element-name: heading
- obj.language: en
- obj.specobject-type: heading
- ChapterName: 9.10.6 Version-dependent unique ID

##### prov-100000012-460892b68f9f465: Version-dependent unique ID (provision)
If provided, the unique ID shall be globally (GUID) or universally (UUID) unique for each fragment across all documents and versions of these.
- bib.al.original-language: en
- bib.dp.publication-date: 2025-03-01
- ids.document: 100000012
- ids.tracing: hash-3F0B90DAAB59D069782A7D445C3E6F837C7E543E939B0DF067E0CF13A71190EE
- obj.clause-number: 9.10.6
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-5c0a9f18eadb460: Version-dependent unique ID (provision)
The unique ID can be used to identify fragments uniquely across all fragments in the target software.
- bib.al.original-language: en
- bib.dp.publication-date: 2025-03-01
- ids.document: 100000012
- ids.tracing: hash-BF9CD4EC19C114283488A6307ECD49C19AAB3F007B4EB4DFBED6597FF981CE0C
- obj.clause-number: 9.10.6
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-7580d02126b848b: Version-dependent unique ID (provision)
The supplier shall provide a unique ID as value of the attribute ids.unique (8.2.1.5) for each SpecObject in the ReqIF™ file.
- bib.al.original-language: en
- bib.dp.publication-date: 2025-03-01
- ids.document: 100000012
- ids.tracing: hash-CF92F71112172A94437BFDE4BB20EA611FA35D97253BB265C2AA0C873495BEC7
- obj.clause-number: 9.10.6
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R134

##### prov-100000012-6efd8ecad6cf4ca: Version-dependent unique ID (provision)
The method for determining values for the unique ID may follow the best-practice identified by the stakeholders relevant for the interoperability context.
- bib.al.original-language: en
- bib.dp.publication-date: 2025-03-01
- ids.document: 100000012
- ids.tracing: hash-392D7E3BA902E904BE869F27B545A86E236566150D0EA5C6FF264F6373BDFD3F
- obj.clause-number: 9.10.6
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-2250837b98094f8: Version-dependent unique ID (provision)
A tracing ID and a unique ID shall be differentiated since one and the same ID cannot be the same over all versions of the same SpecObject (see 9.10.5) as well as uniquely different over all versions of all SpecObjects.
- bib.al.original-language: en
- bib.dp.publication-date: 2025-03-01
- ids.document: 100000012
- ids.tracing: hash-BE1712AC95FA3689C2811F94822AB2E3951F93E492D282283F62BC3BD5A529A6
- obj.clause-number: 9.10.6
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R513

###### prov-100000012-c563000c072f42b: Version-dependent unique ID, Note (provision)
NOTE:
If UUID v5 [10] is used as method for determine values for the unique ID, different stakeholders can achieve generating the same unique value for the same namespace and the same input string.
- bib.al.original-language: en
- bib.dp.publication-date: 2025-03-01
- ids.document: 100000012
- ids.tracing: hash-BEDF14FF4831C8D71A9D6AC9F662CB1E14F5D66B0544BEBF41F1D06BA155252F
- obj.clause-number: 9.10.6
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-100000012-996957e8ccc24fe

### R526: Document asset or service metadata of the creator, supplier, or publisher (pub.*) (heading)
- bib.al.original-language: en
- bib.dp.publication-date: 2025-03-01
- ids.document: 100000012
- obj.clause-number: 9.11
- obj.element-name: heading
- obj.language: en
- obj.specobject-type: heading
- ChapterName: 9.11 Document asset or service metadata of the creator, supplier, or publisher (pub.*)

#### R527: Originator (pub.originator) (heading)
- bib.al.original-language: en
- bib.dp.publication-date: 2025-03-01
- ids.document: 100000012
- obj.clause-number: 9.11.1
- obj.element-name: heading
- obj.language: en
- obj.specobject-type: heading
- ChapterName: 9.11.1 Originator (pub.originator)

##### prov-100000012-e68068bb02684ec: Originator (pub.originator) (provision)
The supplier shall provide the abbreviation or short name of the originator as value of the attribute pub.originator (8.2.2) for each ReqIF™ file of a public standard (see 9.5).
- bib.al.original-language: en
- bib.dp.publication-date: 2025-03-01
- ids.document: 100000012
- ids.tracing: hash-042E0D9127B1ECAFAD463A0E82D3C693AA9BDC552B9E34B690EF4294318B4441
- obj.clause-number: 9.11.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R137
- cross-reference -> R354

##### prov-100000012-b4826575984646a: Originator (pub.originator) (provision)
EXAMPLE:
“DIN*DKE*CEN*CENELEC*IEC*ISO”
- bib.al.original-language: en
- bib.dp.publication-date: 2025-03-01
- ids.document: 100000012
- ids.tracing: hash-4AD6D209C818E2007E9CDBA88A8BEA0B751C1D11586A5C620FA31EDB2F7E71DB
- obj.clause-number: 9.11.1
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-61cb21b2c32c4b2: Originator (pub.originator) (provision)
“DIN*DKE*CEN*CENELEC*IEC*ISO”
- bib.al.original-language: en
- bib.dp.publication-date: 2025-03-01
- ids.document: 100000012
- ids.tracing: hash-76CF5C1D7F3884BAF2BEEB03569B671A550F57EA4C40D115A8D767E27E211901
- obj.clause-number: 9.11.1
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### R531: Harmonization (pub.harmonization) (heading)
- bib.al.original-language: en
- bib.dp.publication-date: 2025-03-01
- ids.document: 100000012
- obj.clause-number: 9.11.2
- obj.element-name: heading
- obj.language: en
- obj.specobject-type: heading
- ChapterName: 9.11.2 Harmonization (pub.harmonization)

##### prov-100000012-0139ef21667841f: Harmonization (pub.harmonization) (provision)
The supplier shall provide the harmonization string for the level of harmonization and version number as value of the attribute pub.harmonization (8.2.2) for each ReqIF™ file of a public standard (see 9.5).
- bib.al.original-language: en
- bib.dp.publication-date: 2025-03-01
- ids.document: 100000012
- ids.tracing: hash-383946F11FE460751EDA4EC218A082FD10E8415A2062AF8E056D662C226F2D21
- obj.clause-number: 9.11.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R137
- cross-reference -> R354

##### prov-100000012-3e38b2026176482: Harmonization (pub.harmonization) (provision)
EXAMPLE:
“IDiS ReqIF™ interpretation for public standards 1.3”
- bib.al.original-language: en
- bib.dp.publication-date: 2025-03-01
- ids.document: 100000012
- ids.tracing: hash-475758CF3360462489161E9C8C9E5E85A19633346F9835DC28B39C3ED24892B1
- obj.clause-number: 9.11.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-f84a15aaa813443: Harmonization (pub.harmonization) (provision)
“IDiS ReqIF™ interpretation for public standards 1.3”
- bib.al.original-language: en
- bib.dp.publication-date: 2025-03-01
- ids.document: 100000012
- ids.tracing: hash-FC43A904FDD33783BC08F187B9E7342877D734F7D827070DBAEA412D7FDCF2E6
- obj.clause-number: 9.11.2
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### R535: Software (pub.software) (heading)
- bib.al.original-language: en
- bib.dp.publication-date: 2025-03-01
- ids.document: 100000012
- obj.clause-number: 9.11.3
- obj.element-name: heading
- obj.language: en
- obj.specobject-type: heading
- ChapterName: 9.11.3 Software (pub.software)

##### prov-100000012-ab3e4e5a1201441: Software (pub.software) (provision)
The supplier shall provide the identification string for software + version as value of the attribute pub.software (8.2.2) for each ReqIF™ file of a public standard (see 9.5).
- bib.al.original-language: en
- bib.dp.publication-date: 2025-03-01
- ids.document: 100000012
- ids.tracing: hash-A1B29744335406BDE6A1D1129E0E120420621CDFC41931B4A7261D9F48F6305F
- obj.clause-number: 9.11.3
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R137
- cross-reference -> R354

##### prov-100000012-8aaac4095534439: Software (pub.software) (provision)
EXAMPLE:
“X-Swift sts2reqif-42.17.4”
- bib.al.original-language: en
- bib.dp.publication-date: 2025-03-01
- ids.document: 100000012
- ids.tracing: hash-76DB3E5C3B4CBD6557910B953CBD793B5E10E86769727382B1F45890EC9DCD95
- obj.clause-number: 9.11.3
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-3f5c00161dff434: Software (pub.software) (provision)
“X-Swift sts2reqif-42.17.4”
- bib.al.original-language: en
- bib.dp.publication-date: 2025-03-01
- ids.document: 100000012
- ids.tracing: hash-3ACAEB14E801ACB8AD0F5DD7BA06353EBB4AC784E458FDE1E07B9C68B2E2412C
- obj.clause-number: 9.11.3
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### R539: Supplier (pub.supplier) (heading)
- bib.al.original-language: en
- bib.dp.publication-date: 2025-03-01
- ids.document: 100000012
- obj.clause-number: 9.11.4
- obj.element-name: heading
- obj.language: en
- obj.specobject-type: heading
- ChapterName: 9.11.4 Supplier (pub.supplier)

##### prov-100000012-dfe1446239734d1: Supplier (pub.supplier) (provision)
The supplier shall provide the abbreviation or short name of the supplier as value of the attribute pub.supplier (8.2.2) for each ReqIF™ file of a public standard (see 9.5).
- bib.al.original-language: en
- bib.dp.publication-date: 2025-03-01
- ids.document: 100000012
- ids.tracing: hash-A389CEA6ED28E5B7F72CDBA5DF5033096A214AADC87A6A5AB1BDB2D61947385F
- obj.clause-number: 9.11.4
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R137
- cross-reference -> R354

##### prov-100000012-3833afec52374d2: Supplier (pub.supplier) (provision)
EXAMPLE:
- “DIN Media”
- “VDE VERLAG”
- bib.al.original-language: en
- bib.dp.publication-date: 2025-03-01
- ids.document: 100000012
- ids.tracing: hash-B3E3D078EE8496D2E12ADEAF90C0271AD7C0B0FC1762B7959FF9FEF1B5B5F819
- obj.clause-number: 9.11.4
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-f95aa164d87e4da: Supplier (pub.supplier), list extract (provision)
| → | - “DIN Media” - “VDE VERLAG” |
| --- | --- |
- bib.al.original-language: en
- bib.dp.publication-date: 2025-03-01
- ids.document: 100000012
- ids.tracing: hash-A8419938061F4E75E80F190585AC640C2898EF1B8CB26969758E0F2E5BAA7CA5
- obj.clause-number: 9.11.4
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

## R543: Presentation (heading)
- bib.al.original-language: en
- bib.dp.publication-date: 2025-03-01
- ids.document: 100000012
- obj.clause-number: 10
- obj.element-name: heading
- obj.language: en
- obj.specobject-type: heading
- ChapterName: 10 Presentation

### R544: Change marks in the text (heading)
- bib.al.original-language: en
- bib.dp.publication-date: 2025-03-01
- ids.document: 100000012
- obj.clause-number: 10.1
- obj.element-name: heading
- obj.language: en
- obj.specobject-type: heading
- ChapterName: 10.1 Change marks in the text

#### prov-100000012-6f1d0e5b84b349e: Change marks in the text (provision)
As change marks in the text of the source document should be supported with a different presentation:
- deletion;
- insertion;
- change (other than explicitly specified deletions or insertions).
- bib.al.original-language: en
- bib.dp.publication-date: 2025-03-01
- ids.document: 100000012
- ids.tracing: hash-94934BA90547408C127A23DF0230FEC9B5ACE5D0908CD7BD77CD56FF14FAF148
- obj.clause-number: 10.1
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

### R546: Labelling and numbering (heading)
- bib.al.original-language: en
- bib.dp.publication-date: 2025-03-01
- ids.document: 100000012
- obj.clause-number: 10.2
- obj.element-name: heading
- obj.language: en
- obj.specobject-type: heading
- ChapterName: 10.2 Labelling and numbering

#### R547: Output position of the label (heading)
- bib.al.original-language: en
- bib.dp.publication-date: 2025-03-01
- ids.document: 100000012
- obj.clause-number: 10.2.1
- obj.element-name: heading
- obj.language: en
- obj.specobject-type: heading
- ChapterName: 10.2.1 Output position of the label

##### prov-100000012-d887757ab49847f: Output position of the label (provision)
The original labelling and numbering of the public standard shall be output as:
- prefix in the content of the SpecObject, i. e. value of either the attribute ReqIF.ChapterName (9.6.1) or the attribute ReqIF.Text (9.6.2); and
- value of the attribute obj.clause-number (9.7.2).
- bib.al.original-language: en
- bib.dp.publication-date: 2025-03-01
- ids.document: 100000012
- ids.tracing: hash-78F7BCBFFF303AE9FF60A4EF27089D8E86859ED1CB122EAB3F20F6954DBE87BC
- obj.clause-number: 10.2.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R387
- cross-reference -> R393
- cross-reference -> R406

#### R549: Presentation aspects for labels (heading)
- bib.al.original-language: en
- bib.dp.publication-date: 2025-03-01
- ids.document: 100000012
- obj.clause-number: 10.2.2
- obj.element-name: heading
- obj.language: en
- obj.specobject-type: heading
- ChapterName: 10.2.2 Presentation aspects for labels

##### prov-100000012-1ea4c3e1d0324cb: Presentation aspects for labels (provision)
Labels and numbering from the document (label) shall be output both as an attribute value and in the content with separators (see Example 1).
- bib.al.original-language: en
- bib.dp.publication-date: 2025-03-01
- ids.document: 100000012
- ids.tracing: hash-80C481C2737BF0BC7AB7628FEA8F590E858EB3E6FD4408F320C1EBA8ADE1B4E8
- obj.clause-number: 10.2.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-fb1449b97016459

##### prov-100000012-fb1449b97016459: Presentation aspects for labels (provision)
EXAMPLE 1:
List items with enumeration letters and period separator included in the output:
<THE-VALUE> <xhtml:div> <xhtml:p xml:lang="en">The organization shall retain documented ...:</xhtml:p> <xhtml:ul> <xhtml:li><xhtml:span>a. </xhtml:span>on the results of the review;</xhtml:li> <xhtml:li><xhtml:span>b. </xhtml:span>on any new requirements ...</xhtml:li> </xhtml:ul> </xhtml:div> <THE-VALUE>
- bib.al.original-language: en
- bib.dp.publication-date: 2025-03-01
- ids.document: 100000012
- ids.tracing: hash-CCA24D2E690D0C08E1503494DC497675EB650F122933B1B9BD30C376854C744C
- obj.clause-number: 10.2.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-9f0db8e7b5a8453: Presentation aspects for labels (provision)
List items with enumeration letters and period separator included in the output:
- bib.al.original-language: en
- bib.dp.publication-date: 2025-03-01
- ids.document: 100000012
- ids.tracing: hash-AF50B460A3DB9AC0D457DB3705BBFEA60106D18A3317A15AFEB974182AF4055E
- obj.clause-number: 10.2.2
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-9eec95cd908d4d7: Presentation aspects for labels (provision)
The format characters before and after the label may be standardized instead of following individual variants of the publishers, as long as this does not affect the interpretation of the provisions (see Example 2).
- bib.al.original-language: en
- bib.dp.publication-date: 2025-03-01
- ids.document: 100000012
- ids.tracing: hash-6D1169DAB2663236C25852F01DDC481D200F15FD51F47C4928ADFD6172B5BDBC
- obj.clause-number: 10.2.2
- obj.element-name: paragraph
- obj.language: en
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-07b47f52d72a498

##### prov-100000012-07b47f52d72a498: Presentation aspects for labels (provision)
EXAMPLE 2:
List items with standard parentheses instead of non-standard variant period as separator:
<THE-VALUE> <xhtml:div> <xhtml:p xml:lang="en">The organization shall retain documented ...:</xhtml:p> <xhtml:ul> <xhtml:li><xhtml:span>a) </xhtml:span>on the results of the review;</xhtml:li> <xhtml:li><xhtml:span>b) </xhtml:span>on any new requirements ...</xhtml:li> </xhtml:ul> </xhtml:div> <THE-VALUE>
- bib.al.original-language: en
- bib.dp.publication-date: 2025-03-01
- ids.document: 100000012
- ids.tracing: hash-0510877950D325FB611881045528D340B3D47EA8DD89076119D6FA6A4AB4B2EE
- obj.clause-number: 10.2.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-a23f1aa9490e4ba: Presentation aspects for labels (provision)
List items with standard parentheses instead of non-standard variant period as separator:
- bib.al.original-language: en
- bib.dp.publication-date: 2025-03-01
- ids.document: 100000012
- ids.tracing: hash-4A0ABD9B15FD7C3F26ED8E78899BB4DE19F8A3469EB0A32F1E51B738518F8C84
- obj.clause-number: 10.2.2
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-b16357a8c6284b1: Presentation aspects for labels (provision)
The entry number for terms shall be output in the SpecObject as a heading, separate from the preferred term, to comply with the structure of terminological entries according to DIN ISO 10241-1 (see Example 3).
- bib.al.original-language: en
- bib.dp.publication-date: 2025-03-01
- ids.document: 100000012
- ids.tracing: hash-9B2D89C1264415BCD7868E046CE3852CB1B2E7431EF5F2F18856D3CCA8B50F49
- obj.clause-number: 10.2.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-100000012-3638e4f87f3c421

##### prov-100000012-3638e4f87f3c421: Presentation aspects for labels (provision)
EXAMPLE 3:
Terminological entry with term number 3.1, the preferred term and the definition.
<THE-VALUE> <xhtml:div> <xhtml:p id="term_3.1" xml:lang="en"><xhtml:b>3.1</xhtml:b></xhtml:p> <xhtml:div xml:lang="en"> <xhtml:div><xhtml:b>local thickness</xhtml:b></xhtml:div> <xhtml:div>the mean of the thickness measurements, of which a ...</xhtml:div> </xhtml:div> </xhtml:div> </THE-VALUE>
- bib.al.original-language: en
- bib.dp.publication-date: 2025-03-01
- ids.document: 100000012
- ids.tracing: hash-221C922EC7E523DCD0A3B7CFBD1405D7863B66974C97A018B4E618871125B8BF
- obj.clause-number: 10.2.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-2d3454c8808446c: Presentation aspects for labels (provision)
Terminological entry with term number 3.1, the preferred term and the definition.
- bib.al.original-language: en
- bib.dp.publication-date: 2025-03-01
- ids.document: 100000012
- ids.tracing: hash-38B186DB391B2F1588B4AFF2F5A9D5EC8994ED7D282B357C353CABCA086337ED
- obj.clause-number: 10.2.2
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### R559: Figures and other types of graphics (heading)
- bib.al.original-language: en
- bib.dp.publication-date: 2025-03-01
- ids.document: 100000012
- obj.clause-number: 10.3
- obj.element-name: heading
- obj.language: en
- obj.specobject-type: heading
- ChapterName: 10.3 Figures and other types of graphics

#### R560: Types of graphics (heading)
- bib.al.original-language: en
- bib.dp.publication-date: 2025-03-01
- ids.document: 100000012
- obj.clause-number: 10.3.1
- obj.element-name: heading
- obj.language: en
- obj.specobject-type: heading
- ChapterName: 10.3.1 Types of graphics

##### prov-100000012-cd7e0e22c5fa43e: Types of graphics (provision)
Provisions for raster images shall be applied for all types of graphics in the ReqIF™ for the public standard (see 10.3.2, 10.3.3, 10.3.4).
- bib.al.original-language: en
- bib.dp.publication-date: 2025-03-01
- ids.document: 100000012
- ids.tracing: hash-7AFC57306C8BD28DE8DAFE926B7F8C2AD5B467558236D66370C49638854EBFA0
- obj.clause-number: 10.3.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R564
- cross-reference -> R566
- cross-reference -> R568

##### prov-100000012-767ba21a05ce416: Types of graphics (provision)
EXAMPLE:
- figures with labelled captions,
- any graphics in tables or in the text,
- formulas rendered as graphics,
- tables rendered as graphics.
- bib.al.original-language: en
- bib.dp.publication-date: 2025-03-01
- ids.document: 100000012
- ids.tracing: hash-DE20C4CAACDAE36BB34669F2D467E07A552C6E402F80C19523B4D2764E837A06
- obj.clause-number: 10.3.1
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-100000012-587e7834be344af: Types of graphics, list extract (provision)
| → | - figures with labelled captions, - any graphics in tables or in the text, - formulas rendered as graphics, - tables rendered as graphics. |
| --- | --- |
- bib.al.original-language: en
- bib.dp.publication-date: 2025-03-01
- ids.document: 100000012
- ids.tracing: hash-CC01FCFBBE2DF453977D50C63229307B9E446A03B0086FFDC03D642D64AB0A0E
- obj.clause-number: 10.3.1
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### R564: Graphics format (heading)
- bib.al.original-language: en
- bib.dp.publication-date: 2025-03-01
- ids.document: 100000012
- obj.clause-number: 10.3.2
- obj.element-name: heading
- obj.language: en
- obj.specobject-type: heading
- ChapterName: 10.3.2 Graphics format

##### prov-100000012-ea1ec3fc17ac40b: Graphics format (provision)
The supplier shall provide all graphics as Portable Network Graphics (PNG).
- bib.al.original-language: en
- bib.dp.publication-date: 2025-03-01
- ids.document: 100000012
- ids.tracing: hash-737AC5FC135360B1BA5FF02A3BD79344F09AAEA7190A078602939350D89ED9EA
- obj.clause-number: 10.3.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### R566: Graphics compression (heading)
- bib.al.original-language: en
- bib.dp.publication-date: 2025-03-01
- ids.document: 100000012
- obj.clause-number: 10.3.3
- obj.element-name: heading
- obj.language: en
- obj.specobject-type: heading
- ChapterName: 10.3.3 Graphics compression

##### prov-100000012-6e28bc4133e3480: Graphics compression (provision)
The supplier should provide all graphics using the lossless compression optimized for minimal file size to ensure fast processing and to save storage space.
- bib.al.original-language: en
- bib.dp.publication-date: 2025-03-01
- ids.document: 100000012
- ids.tracing: hash-D2D5040D54F519F1747E5813AE1E9528867816D2EC9729DBC02D6476CECDAC29
- obj.clause-number: 10.3.3
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

#### R568: Graphics resolution (heading)
- bib.al.original-language: en
- bib.dp.publication-date: 2025-03-01
- ids.document: 100000012
- obj.clause-number: 10.3.4
- obj.element-name: heading
- obj.language: en
- obj.specobject-type: heading
- ChapterName: 10.3.4 Graphics resolution

##### prov-100000012-f0af8e0c2873427: Graphics resolution (provision)
The supplier shall provide all graphics in a resolution that can be rendered without issues relevant for the interpretation of provisions.
- bib.al.original-language: en
- bib.dp.publication-date: 2025-03-01
- ids.document: 100000012
- ids.tracing: hash-F58D84361EEBF062C156DEA7DD14157A34A63DBC5F0F308D232A1C9DBC6ACF12
- obj.clause-number: 10.3.4
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### prov-100000012-a2e7c42af75041b: Graphics resolution, Note (provision)
NOTE:
Following conventions for ISO, IEC, CEN, CENELEC, DIN and DKE deliverables, recommended resolutions are:
- If online variants with anti-aliasing are included, the resolution should be 90 dpi or higher.
- If print variants are included, the resolution should be 600 dpi.
- bib.al.original-language: en
- bib.dp.publication-date: 2025-03-01
- ids.document: 100000012
- ids.tracing: hash-78A30177B8144712911B6A1DDAB173A3A608827482541B79312CAFC5391861F5
- obj.clause-number: 10.3.4
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### R571: Formulas (heading)
- bib.al.original-language: en
- bib.dp.publication-date: 2025-03-01
- ids.document: 100000012
- obj.clause-number: 10.4
- obj.element-name: heading
- obj.language: en
- obj.specobject-type: heading
- ChapterName: 10.4 Formulas

#### R572: Formula format (heading)
- bib.al.original-language: en
- bib.dp.publication-date: 2025-03-01
- ids.document: 100000012
- obj.clause-number: 10.4.1
- obj.element-name: heading
- obj.language: en
- obj.specobject-type: heading
- ChapterName: 10.4.1 Formula format

##### prov-100000012-9401da55de874a0: Formula format (provision)
For character-encoded output, MathML 3.0 presentational markup shall be used according to ISO/IEC 40314.
- bib.al.original-language: en
- bib.dp.publication-date: 2025-03-01
- ids.document: 100000012
- ids.tracing: hash-93561175067456873D42973BC7613641BB38E63BADEEE2E1705C3858BE51819D
- obj.clause-number: 10.4.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-c0471cb3c8eb426: Formula format (provision)
To ensure rendering in common web browsers, all MathML markup shall be output according to the W3C MathML Core subset.
- bib.al.original-language: en
- bib.dp.publication-date: 2025-03-01
- ids.document: 100000012
- ids.tracing: hash-39E38083B0533E24B5B5EE64B4CAC3F5355D1C7E03E78650A0E5F7B54CA0BE41
- obj.clause-number: 10.4.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### prov-100000012-7c4b284669474c3: Formula format, Note (provision)
NOTE:
For more information about MathML in web browsers see [11].
- bib.al.original-language: en
- bib.dp.publication-date: 2025-03-01
- ids.document: 100000012
- ids.tracing: hash-0ACA6309C68BEEDBFE8CF7FC3DC527239161A2E184431A29FC3C12CB8B172D39
- obj.clause-number: 10.4.1
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-100000012-996957e8ccc24fe

#### R576: Formula output (heading)
- bib.al.original-language: en
- bib.dp.publication-date: 2025-03-01
- ids.document: 100000012
- obj.clause-number: 10.4.2
- obj.element-name: heading
- obj.language: en
- obj.specobject-type: heading
- ChapterName: 10.4.2 Formula output

##### prov-100000012-4bed30c4a06345a: Formula output (provision)
- If the source document is an XML instance, the formulas shall be output in the MathML (see 10.4.1) format.
- If character-encoded output is not supported in the target software, all formulas shall be output as graphics (see 10.3.1) to ensure a rendering even.
- bib.al.original-language: en
- bib.dp.publication-date: 2025-03-01
- ids.document: 100000012
- ids.tracing: hash-258FDF23D9DB13FB8450FA2B4247167B88A4356CD768D45057F77AF85FEEE33E
- obj.clause-number: 10.4.2
- obj.element-name: unordered-list
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-100000012-09367183ace9409: Formula output, list extract (provision)
| → | If the source document is an XML instance, the formulas shall be output in the MathML (see 10.4.1) format. |
| --- | --- |
- bib.al.original-language: en
- bib.dp.publication-date: 2025-03-01
- ids.document: 100000012
- ids.tracing: hash-F98B6C4B461DA6EDE0C2AB8F74FD3D8913735506C930E993FE0E833D8DD8BBDE
- obj.clause-number: 10.4.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R572

###### prov-100000012-d348d54cc20d4fe: Formula output, list extract (provision)
| → | If character-encoded output is not supported in the target software, all formulas shall be output as graphics (see 10.3.1) to ensure a rendering even. |
| --- | --- |
- bib.al.original-language: en
- bib.dp.publication-date: 2025-03-01
- ids.document: 100000012
- ids.tracing: hash-2F4EBB4A038B4A6718A9A9F9395374C91BB0C7F7366AE99CD1B4C9A7DF61B3A4
- obj.clause-number: 10.4.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R560

##### prov-100000012-fba14dd0a14b4e5: Formula output (provision)
All formula variants shall be output as attachments to facilitate re-use of the information.
- bib.al.original-language: en
- bib.dp.publication-date: 2025-03-01
- ids.document: 100000012
- ids.tracing: hash-AA35416E8FA06F5BEAD73B699ED842B6B374D54EDC9B6A9D23526C283FC54C60
- obj.clause-number: 10.4.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-2c010c985aa3471: Formula output (provision)
All formulas shall be output within the XHTML™ 1.0 at the position where they appear in the source text.
- bib.al.original-language: en
- bib.dp.publication-date: 2025-03-01
- ids.document: 100000012
- ids.tracing: hash-8938AD58426876AFCF4929808D074D0FA9341459AC75536F8DB02297FA7592D9
- obj.clause-number: 10.4.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-e4980f77525f435: Formula output (provision)
EXAMPLE: <THE-VALUE> <xhtml:div> <xhtml:p xml:lang="en"> <xhtml:object data="formulas/42.mml" type="application/mathml-presentation+xml"> <xhtml:object data="formulas/42.png" type="image/png">Formula missing!</xhtml:object> </xhtml:object> </xhtml:p> </xhtml:div> </THE-VALUE>
- bib.al.original-language: en
- bib.dp.publication-date: 2025-03-01
- ids.document: 100000012
- ids.tracing: hash-C59ABAFAF80FEDCAADF5EBC60533AD3338D49BC82E430B80621123750E910916
- obj.clause-number: 10.4.2
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### R583: Dissolve in-line formulas (heading)
- bib.al.original-language: en
- bib.dp.publication-date: 2025-03-01
- ids.document: 100000012
- obj.clause-number: 10.4.3
- obj.element-name: heading
- obj.language: en
- obj.specobject-type: heading
- ChapterName: 10.4.3 Dissolve in-line formulas

##### prov-100000012-36e056432a6e47f: Dissolve in-line formulas (provision)
To optimize the machine-processing and reading flow, in-line formulas should be resolved if they:
- can be substituted with text formatting in XHTML™ 1.0.
- do not contain any formula characters that cannot be displayed as XHTML™ 1.0 text.
- bib.al.original-language: en
- bib.dp.publication-date: 2025-03-01
- ids.document: 100000012
- ids.tracing: hash-7BD8ED0CA7D615844C8B9275C7A51AA2C71811CDF044DCD3204638D22794A651
- obj.clause-number: 10.4.3
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-cc287cac19b241f: Dissolve in-line formulas (provision)
Text formatting should be substituted in XHTML™ 1.0:
- fractions, provided they can be represented with a slash (/), i. e. if numerator and denominator are no complex terms and can be represented without additional parenthesis;
- bold (<b>);
- upright (null);
- superscript (<sup>);
- parentheses and posts if trivialisable ({[(|)]});
- italics (<i>);
- small caps font (small caps);
- typewriter font (<tt>);
- font with serifs (<serif>);
- serifless font (<sans-serif>);
- subscript (<sub>).
- bib.al.original-language: en
- bib.dp.publication-date: 2025-03-01
- ids.document: 100000012
- ids.tracing: hash-060B233D1D5890439AD53C9EB6155DC69A54C0CA828654B1504E1A72FB1BBEC9
- obj.clause-number: 10.4.3
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-f873b93bc94246f: Dissolve in-line formulas (provision)
EXAMPLE: <xhtml:p xml:lang="en">The Einstein insight is <xhtml:span style="font-family:Cambria Math,Times,serif"><xhtml:i>E</xhtml:i> = <xhtml:i>m</xhtml:i> c<xhtml:sup>2</xhtml:sup><xhtml:span>.</xhtml:p>
- bib.al.original-language: en
- bib.dp.publication-date: 2025-03-01
- ids.document: 100000012
- ids.tracing: hash-D4E74CE9229BCB5402E38DFABC26793F52CA60AF805A6DE9DCD88D5C1AEA9B9D
- obj.clause-number: 10.4.3
- obj.element-name: example
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### R587: Footnotes (heading)
- bib.al.original-language: en
- bib.dp.publication-date: 2025-03-01
- ids.document: 100000012
- obj.clause-number: 10.5
- obj.element-name: heading
- obj.language: en
- obj.specobject-type: heading
- ChapterName: 10.5 Footnotes

#### prov-100000012-0121cc76aa4743e: Footnotes (provision)
The content of all footnotes referenced within a SpecObject shall be embedded so that each SpecObject contains the complete information of the referenced footnotes.
- bib.al.original-language: en
- bib.dp.publication-date: 2025-03-01
- ids.document: 100000012
- ids.tracing: hash-00780A4618EFAB94F2234E52BE009C42899BFC791C17048A3CA95CE6AFBDDD0D
- obj.clause-number: 10.5
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-3f6d00a94acc4a3: Footnotes (provision)
- Figure footnotes shall be output at the end of the legend.
- Table footnotes shall be output at the end of the table.
- Text footnotes shall be output as a child SpecObject in which the footnote is referenced.
- bib.al.original-language: en
- bib.dp.publication-date: 2025-03-01
- ids.document: 100000012
- ids.tracing: hash-B58F83ACE1A1865404655018227FC2D4B89F44E98E946A27B105FA1361DFEBE3
- obj.clause-number: 10.5
- obj.element-name: unordered-list
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-e55f6434d711428: Footnotes, list extract (provision)
| → | Figure footnotes shall be output at the end of the legend. |
| --- | --- |
- bib.al.original-language: en
- bib.dp.publication-date: 2025-03-01
- ids.document: 100000012
- ids.tracing: hash-7AD72E122A10094CAF329F913A85B0A0ED319656215F7E1C9D5081BDA143FF07
- obj.clause-number: 10.5
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-4236fd1b3a4f46c: Footnotes, list extract (provision)
| → | Table footnotes shall be output at the end of the table. |
| --- | --- |
- bib.al.original-language: en
- bib.dp.publication-date: 2025-03-01
- ids.document: 100000012
- ids.tracing: hash-5EF516376A7B1932D7FC31A980A858304212F9C6581576C5781BF2A088A91C64
- obj.clause-number: 10.5
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-c4f7b52a99a7437: Footnotes, list extract (provision)
| → | Text footnotes shall be output as a child SpecObject in which the footnote is referenced. |
| --- | --- |
- bib.al.original-language: en
- bib.dp.publication-date: 2025-03-01
- ids.document: 100000012
- ids.tracing: hash-D37158FB925A82C98134A11264C989F1FCB791DBDC9143F0D6E18F605A89A3E2
- obj.clause-number: 10.5
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### R593: Tables (heading)
- bib.al.original-language: en
- bib.dp.publication-date: 2025-03-01
- ids.document: 100000012
- obj.clause-number: 10.6
- obj.element-name: heading
- obj.language: en
- obj.specobject-type: heading
- ChapterName: 10.6 Tables

#### R594: Table format (heading)
- bib.al.original-language: en
- bib.dp.publication-date: 2025-03-01
- ids.document: 100000012
- obj.clause-number: 10.6.1
- obj.element-name: heading
- obj.language: en
- obj.specobject-type: heading
- ChapterName: 10.6.1 Table format

##### prov-100000012-b554fff8f43c4f0: Table format (provision)
To ensure rendering in common target software, all table markup shall be output according to the W3C Basic Table Module of the XHTML™ Modularization 1.1.
- bib.al.original-language: en
- bib.dp.publication-date: 2025-03-01
- ids.document: 100000012
- ids.tracing: hash-EC4EC988BCA1A9949E6E251DC8F3A82BC755A6A32F75FEEA6D7F5B3929590CA9
- obj.clause-number: 10.6.1
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### R596: Table output (heading)
- bib.al.original-language: en
- bib.dp.publication-date: 2025-03-01
- ids.document: 100000012
- obj.clause-number: 10.6.2
- obj.element-name: heading
- obj.language: en
- obj.specobject-type: heading
- ChapterName: 10.6.2 Table output

##### prov-100000012-9c8977fe1f1e4e1: Table output (provision)
- If the source document is an XML instance, the tables shall be output in the HTML table (see 10.6.1) format.
- A table may be output as graphics (see 10.3.1) at the position where it appears in the text, only if it cannot be rendered in the HTML table format without issues relevant for the interpretation of provisions.
- bib.al.original-language: en
- bib.dp.publication-date: 2025-03-01
- ids.document: 100000012
- ids.tracing: hash-81796A60507168264FD2AB8B3CF1147513B9B57CE0775F9A309866F7F530BA6B
- obj.clause-number: 10.6.2
- obj.element-name: unordered-list
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-100000012-5bc79657d5054cc: Table output, list extract (provision)
| → | If the source document is an XML instance, the tables shall be output in the HTML table (see 10.6.1) format. |
| --- | --- |
- bib.al.original-language: en
- bib.dp.publication-date: 2025-03-01
- ids.document: 100000012
- ids.tracing: hash-B3F722076E627E24E80DA0C6A3CE8562DCC2BCE18D645C760EBDDC289B321F3D
- obj.clause-number: 10.6.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R594

###### prov-100000012-d7cf71d919d145c: Table output, list extract (provision)
| → | A table may be output as graphics (see 10.3.1) at the position where it appears in the text, only if it cannot be rendered in the HTML table format without issues relevant for the interpretation of provisions. |
| --- | --- |
- bib.al.original-language: en
- bib.dp.publication-date: 2025-03-01
- ids.document: 100000012
- ids.tracing: hash-3A1B2C46120005D896615FF27225DE927AEA1D1E1E39477792CA9EB22DA9CF89
- obj.clause-number: 10.6.2
- obj.element-name: paragraph
- obj.language: en
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R560

##### prov-100000012-d3f45bb8402d48f: Table output (provision)
All table variants shall be output as attachments to facilitate re-use of the information.
- bib.al.original-language: en
- bib.dp.publication-date: 2025-03-01
- ids.document: 100000012
- ids.tracing: hash-D6079EB60300662598CAD001C966C1BB539A94386FE4F2ECB68928E70A4D8734
- obj.clause-number: 10.6.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-2db06d65718e46f: Table output (provision)
All tables shall be output within the XHTML™ 1.0 at the position where they appear in the source text.
- bib.al.original-language: en
- bib.dp.publication-date: 2025-03-01
- ids.document: 100000012
- ids.tracing: hash-49916412A1CF48AB6FB24AE48FB68DF4346CDF9273CC575770F16C26A5CE0688
- obj.clause-number: 10.6.2
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### R602: Normalization of tables (heading)
- bib.al.original-language: en
- bib.dp.publication-date: 2025-03-01
- ids.document: 100000012
- obj.clause-number: 10.6.3
- obj.element-name: heading
- obj.language: en
- obj.specobject-type: heading
- ChapterName: 10.6.3 Normalization of tables

##### prov-100000012-e3eaf6e02a284e8: Normalization of tables (provision)
The following HTML table markup shall be output so that the tables can be rendered in the target software without issues relevant for the interpretation of provisions:
- column separators;
- horizontal alignment;
- horizontal spans;
- row separators;
- vertical alignment;
- vertical spans.
- bib.al.original-language: en
- bib.dp.publication-date: 2025-03-01
- ids.document: 100000012
- ids.tracing: hash-88FD5A2327A66D69F518B158BA61D835F42CAC0607FCCE481C684CE1B25D2F5E
- obj.clause-number: 10.6.3
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

## R604: Digital material to the ReqIF™ interpretation for public standards (heading)
- bib.al.original-language: en
- bib.dp.publication-date: 2025-03-01
- ids.document: 100000012
- obj.clause-number: 11
- obj.element-name: heading
- obj.language: en
- obj.specobject-type: heading
- ChapterName: 11 Digital material to the ReqIF™ interpretation for public standards

### R605: Benchmarking (heading)
- bib.al.original-language: en
- bib.dp.publication-date: 2025-03-01
- ids.document: 100000012
- obj.clause-number: 11.1
- obj.element-name: heading
- obj.language: en
- obj.specobject-type: heading
- ChapterName: 11.1 Benchmarking

#### prov-100000012-ed1dbde09f934f4: Benchmarking (provision)
To validate the level of conformance to this specification, DIN and DKE provide a test set of ReqIF™ files for publicly available technical rules or publicly available legislative regulations, currently:
- testnorm.reqifz: ReqIF™ file for benchmarking the rendition of the standard elements for technical rules.
- testpublication.reqifz: ReqIF™ file for benchmarking the rendition of the standard elements for secondary content.
- testrequirements.reqifz: ReqIF™ file for benchmarking the pre-classification of attribute with values, the fragmentation of the source document and the recognition of sentences in the source document.
- bib.al.original-language: en
- bib.dp.publication-date: 2025-03-01
- ids.document: 100000012
- ids.tracing: hash-F705B3F7BBD1ACEBB835476A6742282FAF483E13F01A571E12AE28A8F778EAB7
- obj.clause-number: 11.1
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### R607: Examples (heading)
- bib.al.original-language: en
- bib.dp.publication-date: 2025-03-01
- ids.document: 100000012
- obj.clause-number: 11.2
- obj.element-name: heading
- obj.language: en
- obj.specobject-type: heading
- ChapterName: 11.2 Examples

#### prov-100000012-c84435bc7bd5469: Examples (provision)
To facilitate the use of this specification, DIN and DKE provide a test set of ReqIF™ files as examples for publicly available technical rules or publicly available legislative regulations.
- bib.al.original-language: en
- bib.dp.publication-date: 2025-03-01
- ids.document: 100000012
- ids.tracing: hash-DC8974E2840A930BCC27ADC2306A15ECADF94D3EF270B8F49E11FCBA57055DC0
- obj.clause-number: 11.2
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### R609: Tables to the data model (heading)
- bib.al.original-language: en
- bib.dp.publication-date: 2025-03-01
- ids.document: 100000012
- obj.clause-number: 11.3
- obj.element-name: heading
- obj.language: en
- obj.specobject-type: heading
- ChapterName: 11.3 Tables to the data model

#### prov-100000012-25b45cdb1b5a4dc: Tables to the data model (provision)
To facilitate the use of this specification, the several tables can be obtained as MS® Excel® ^3 file from the official web page for this specification, currently:
- user stories for requirements engineering (see Annex A);
- data model (see 8.2 and 8.3);
- long name and identifier syntax (see 8.4);
- class name abbreviations (see 8.5);
- standards for document metadata (see the Metadata Field Specification);
- update flag: actual values and definitions (see the Metadata Field Specification);
- document type: actual values and definitions (see the Metadata Field Specification);
- attribute and content outputs: checklists for implementing 9.2;
- supplementary source information.
- bib.al.original-language: en
- bib.dp.publication-date: 2025-03-01
- ids.document: 100000012
- ids.tracing: hash-10D85189AA3DB029A97BA698E7E1F0F0CB0A6D91510D8CF61CFD90CB1AE40377
- obj.clause-number: 11.3
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R619
- cross-reference -> R119
- cross-reference -> R140
- cross-reference -> R177
- cross-reference -> R202
- cross-reference -> R237

##### prov-100000012-e0c22d899a8c421: Tables to the data model, Note (provision)
NOTE:
As added value to the tables in the document, predefined collapsable groups and filters for all columns can be used in the MS® Excel® ^3 file.
- bib.al.original-language: en
- bib.dp.publication-date: 2025-03-01
- ids.document: 100000012
- ids.tracing: hash-9686396F02E3EE3F742BE1A9AEE2BC1110C80F779F441C0E738B4EB4707DBA06
- obj.clause-number: 11.3
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### R612: Utilities for the import and export processes (scripts or templates) (heading)
- bib.al.original-language: en
- bib.dp.publication-date: 2025-03-01
- ids.document: 100000012
- obj.clause-number: 11.4
- obj.element-name: heading
- obj.language: en
- obj.specobject-type: heading
- ChapterName: 11.4 Utilities for the import and export processes (scripts or templates)

#### prov-100000012-efd981e9ec034c6: Utilities for the import and export processes (scripts or templates) (provision)
If the automatization of the import process shall be improved, the scripts or templates deliverables can be obtained from the official web page for this specification.
- bib.al.original-language: en
- bib.dp.publication-date: 2025-03-01
- ids.document: 100000012
- ids.tracing: hash-1AB72F03A6634D7CA879D8BEA6AE359F5B7DDFB7779AF4D9B3AB34D69527791B
- obj.clause-number: 11.4
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-0b802555111340d: Utilities for the import and export processes (scripts or templates), Note (provision)
NOTE:
If supported by the target software, the use of import or project templates can accelerate or simplify the process by creating the desired sequence of the attributes instead of the common alphabetical default order.
- bib.al.original-language: en
- bib.dp.publication-date: 2025-03-01
- ids.document: 100000012
- ids.tracing: hash-FE27C105D8A58627D8A5C484A04D56088D984BFF55257640CAB84B9C70B53A80
- obj.clause-number: 11.4
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### R615: Validating the data model release 1.3 (Schematron) (heading)
- bib.al.original-language: en
- bib.dp.publication-date: 2025-03-01
- ids.document: 100000012
- obj.clause-number: 11.5
- obj.element-name: heading
- obj.language: en
- obj.specobject-type: heading
- ChapterName: 11.5 Validating the data model release 1.3 (Schematron)

#### prov-100000012-341f9551d1904b9: Validating the data model release 1.3 (Schematron) (provision)
If a ReqIF™ file shall be validated against this specification, the Schematron deliverables can be obtained from the official web page for this specification.
- bib.al.original-language: en
- bib.dp.publication-date: 2025-03-01
- ids.document: 100000012
- ids.tracing: hash-A33EF06FE8E9F18F78E62F4D30D6848E7F4CA5E7EF98193C8E4D08AFF38250F1
- obj.clause-number: 11.5
- obj.element-name: paragraph
- obj.language: en
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-02836a5b843a455: Validating the data model release 1.3 (Schematron) (provision)
Validating against this specification using this Schematron should not be mixed up with the validation of the ReqIF™ 1.2 format using the corresponding XML Schema Definition.
- bib.al.original-language: en
- bib.dp.publication-date: 2025-03-01
- ids.document: 100000012
- ids.tracing: hash-B1C8495B30E668344EE86AB48E4290A1A5991DB4E691AE1728A9D48A986A20CA
- obj.clause-number: 11.5
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

##### prov-100000012-1e5398cf9e17435: Validating the data model release 1.3 (Schematron), Note (provision)
NOTE:
For the Schematron specification see ISO/IEC 19757-3.
- bib.al.original-language: en
- bib.dp.publication-date: 2025-03-01
- ids.document: 100000012
- ids.tracing: hash-52DEC50BEEC28B7DFC26520143BB5E8AAF1DEFDA09FD09ED4BD56D6F29831C09
- obj.clause-number: 11.5
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

## R619: User stories for requirements engineering (heading)
- bib.al.original-language: en
- bib.dp.publication-date: 2025-03-01
- ids.document: 100000012
- obj.clause-number: Annex A
- obj.element-name: heading
- obj.language: en
- obj.specobject-type: heading
- ChapterName: Annex A User stories for requirements engineering

### prov-100000012-7430f5661e4e406: User stories for requirements engineering (provision)
As requirements engineer, I would like to be able to filter SpecObject by metadata.
- bib.al.original-language: en
- bib.dp.publication-date: 2025-03-01
- ids.document: 100000012
- ids.tracing: hash-CE58BDEA3C94B5088C2088EEAC4FE5EA33E6A1572E4BB31A605A37C3AFB6AA7B
- obj.clause-number: Annex A
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-100000012-c419563f2668424: User stories for requirements engineering (provision)
As requirements engineer, I want to be able to search SpecObject for metadata.
- bib.al.original-language: en
- bib.dp.publication-date: 2025-03-01
- ids.document: 100000012
- ids.tracing: hash-AB79B8521679662D08EA9FCCD8C266B560640CC03179C12C82DAA79330CA2FBA
- obj.clause-number: Annex A
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-100000012-600d74c39506429: User stories for requirements engineering (provision)
As requirements engineer, I want to be able to determine from which document and from which edition the SpecObject originates (source).
- bib.al.original-language: en
- bib.dp.publication-date: 2025-03-01
- ids.document: 100000012
- ids.tracing: hash-78145A761B72E4D3DDDE3E463704EFEE3E34841218EAB1CDC8ADBDF0F2CD9888
- obj.clause-number: Annex A
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-100000012-0e690acf1b1e460: User stories for requirements engineering (provision)
As requirements engineer, I want to be able to track changes to an actual SpecObject compared to one from previous editions.
- bib.al.original-language: en
- bib.dp.publication-date: 2025-03-01
- ids.document: 100000012
- ids.tracing: hash-5A6BDA65A8CD90A8BC809562258F8644BBB4D6B7E5BC014CA986067F0BBB232A
- obj.clause-number: Annex A
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-100000012-83b688e34562405: User stories for requirements engineering (provision)
As requirements engineer, I want to be able to trace the impact of amendment documents or correction documents on a SpecObject.
- bib.al.original-language: en
- bib.dp.publication-date: 2025-03-01
- ids.document: 100000012
- ids.tracing: hash-4253A221790FF7FB60A2C81C1E176AC7CEC6FF406FE9111DBBFD6D197BCD116A
- obj.clause-number: Annex A
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-100000012-340f9335995e41c: User stories for requirements engineering (provision)
As requirements engineer, I want to be able to find the corresponding SpecObject source for a SpecObject, regardless of where it is located and where it has been moved to (single source of truth).
- bib.al.original-language: en
- bib.dp.publication-date: 2025-03-01
- ids.document: 100000012
- ids.tracing: hash-3A44225466F4E522249CF05D83B86329A99DF87B3F6BF861EE07DE2699ADC5BE
- obj.clause-number: Annex A
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-100000012-a491f2dda0934f2: User stories for requirements engineering (provision)
As requirements engineer, I need the document identifier as an attribute on each SpecObject in order to be able to establish the relationship to the source and its metadata.
- bib.al.original-language: en
- bib.dp.publication-date: 2025-03-01
- ids.document: 100000012
- ids.tracing: hash-15DAA328F2CDDD6A38D43D1828C8BD50768EF0DB1C34EDE7929228CC514B61C7
- obj.clause-number: Annex A
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-100000012-2b05dfd84506457: User stories for requirements engineering (provision)
As requirements engineer, I want to be able to jump to the applicable standards.
- bib.al.original-language: en
- bib.dp.publication-date: 2025-03-01
- ids.document: 100000012
- ids.tracing: hash-BA7EC6D470F6167EA863072A3A77159FA0BDE9689C5852DD723591431E8A162A
- obj.clause-number: Annex A
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

## R628: Background on identifiers (IDs) (heading)
- bib.al.original-language: en
- bib.dp.publication-date: 2025-03-01
- ids.document: 100000012
- obj.clause-number: Annex B
- obj.element-name: heading
- obj.language: en
- obj.specobject-type: heading
- ChapterName: Annex B Background on identifiers (IDs)

### R629: User Stories for identifiers (IDs) (heading)
- bib.al.original-language: en
- bib.dp.publication-date: 2025-03-01
- ids.document: 100000012
- obj.clause-number: B.1
- obj.element-name: heading
- obj.language: en
- obj.specobject-type: heading
- ChapterName: B.1 User Stories for identifiers (IDs)

#### prov-100000012-dac5dfbf62bf494: User Stories for identifiers (IDs) (provision)
- As user of a SpecObject I want to identify documents uniquely using machine-resolvable database keys (document IDs).
- As user of a SpecObject I want to be able to link to fragments within target documents, using speaking identifiers (IDs) based on the references within the source document (element IDs).
- As user of a SpecObject I want to identify synoptic elements in different language variants for the same version of the same document (language-independent IDs).
- As user of a SpecObject I want to identify fragments uniquely by using path and offset independently or below the element contexts given in the content (path IDs).
- As user of a SpecObject I want to make fragments unambiguously traceable across the versions of the same context (version-independent tracing IDs).
- As user of a SpecObject I want to identify fragments uniquely, using globally (GUID), universally (UUID) or other unique identifiers (version-independent unique IDs).
- bib.al.original-language: en
- bib.dp.publication-date: 2025-03-01
- ids.document: 100000012
- ids.tracing: hash-8C8849F263BACA3DFAA277117FCE66998BBCABA0491F52E788835BF7A2E6E354
- obj.clause-number: B.1
- obj.element-name: unordered-list
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-b24527c390c649c: User Stories for identifiers (IDs), list extract (provision)
| → | As user of a SpecObject I want to identify documents uniquely using machine-resolvable database keys (document IDs). |
| --- | --- |
- bib.al.original-language: en
- bib.dp.publication-date: 2025-03-01
- ids.document: 100000012
- ids.tracing: hash-0ECEA0A41FE620D1877DFA4CBAD6BF93CA329505454EB134CA10F41ECEA57773
- obj.clause-number: B.1
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-e5c6e905865b4f8: User Stories for identifiers (IDs), list extract (provision)
| → | As user of a SpecObject I want to be able to link to fragments within target documents, using speaking identifiers (IDs) based on the references within the source document (element IDs). |
| --- | --- |
- bib.al.original-language: en
- bib.dp.publication-date: 2025-03-01
- ids.document: 100000012
- ids.tracing: hash-6CD9E1B55B3C747AC03BA0C40A95F74B46BDDFA3F1D4BFFFBF66AC64534AB945
- obj.clause-number: B.1
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-c590f2282f3d4fe: User Stories for identifiers (IDs), list extract (provision)
| → | As user of a SpecObject I want to identify synoptic elements in different language variants for the same version of the same document (language-independent IDs). |
| --- | --- |
- bib.al.original-language: en
- bib.dp.publication-date: 2025-03-01
- ids.document: 100000012
- ids.tracing: hash-5B6353156B90BF38F6222B12D06354CAF52A327F0E73A63BD0A0442720C568FD
- obj.clause-number: B.1
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-0ffe81efb98044d: User Stories for identifiers (IDs), list extract (provision)
| → | As user of a SpecObject I want to identify fragments uniquely by using path and offset independently or below the element contexts given in the content (path IDs). |
| --- | --- |
- bib.al.original-language: en
- bib.dp.publication-date: 2025-03-01
- ids.document: 100000012
- ids.tracing: hash-6546D25A534EAEF08FB07029317DCF99C50D8C14A63D70E8E98E15EAD3640951
- obj.clause-number: B.1
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-8c8fc87a19c74ad: User Stories for identifiers (IDs), list extract (provision)
| → | As user of a SpecObject I want to make fragments unambiguously traceable across the versions of the same context (version-independent tracing IDs). |
| --- | --- |
- bib.al.original-language: en
- bib.dp.publication-date: 2025-03-01
- ids.document: 100000012
- ids.tracing: hash-35BA48F1E77FBEA65F400DA18DE2BCFE00FFE60717D2A7BDA5DC839D8B810749
- obj.clause-number: B.1
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-36e31f4c66214c0: User Stories for identifiers (IDs), list extract (provision)
| → | As user of a SpecObject I want to identify fragments uniquely, using globally (GUID), universally (UUID) or other unique identifiers (version-independent unique IDs). |
| --- | --- |
- bib.al.original-language: en
- bib.dp.publication-date: 2025-03-01
- ids.document: 100000012
- ids.tracing: hash-BCD65EF408A98158AD4D07805B763C163E27030A77C121A8DF577D3D9D01B203
- obj.clause-number: B.1
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### R637: Initial situation for ID systems (heading)
- bib.al.original-language: en
- bib.dp.publication-date: 2025-03-01
- ids.document: 100000012
- obj.clause-number: B.2
- obj.element-name: heading
- obj.language: en
- obj.specobject-type: heading
- ChapterName: B.2 Initial situation for ID systems

#### prov-100000012-4b35d69500c2452: Initial situation for ID systems (provision)
- ID systems are already established for some requirements, but not for others.
- Some ID systems are already included throughout the content, for example document IDs and element IDs.
- Some ID systems cannot be provided in the content, i. e. some ID systems shall be located outside the content, for example using RDF.
- Since some requirements are incompatible, no ID system can cover all requirements, so that several ID systems shall be supplied.
- bib.al.original-language: en
- bib.dp.publication-date: 2025-03-01
- ids.document: 100000012
- ids.tracing: hash-F09D67139B064990D27DCAAD39786EB81CB7A8F3C456E9413F0278DB9F9EBBD5
- obj.clause-number: B.2
- obj.element-name: unordered-list
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-6992b617cbe34e5: Initial situation for ID systems, list extract (provision)
| → | ID systems are already established for some requirements, but not for others. |
| --- | --- |
- bib.al.original-language: en
- bib.dp.publication-date: 2025-03-01
- ids.document: 100000012
- ids.tracing: hash-151AF701A8B6FA60D8CBE901E0E4B6FC0430F339061D6D2E6FF8F8605BD5245D
- obj.clause-number: B.2
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-1f42ffff06f54af: Initial situation for ID systems, list extract (provision)
| → | Some ID systems are already included throughout the content, for example document IDs and element IDs. |
| --- | --- |
- bib.al.original-language: en
- bib.dp.publication-date: 2025-03-01
- ids.document: 100000012
- ids.tracing: hash-E7BA14AC7E94C7A30577F118D650360ABE6AB7A5824489B02C2A21EF4E2F364C
- obj.clause-number: B.2
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-369a55556efe4ea: Initial situation for ID systems, list extract (provision)
| → | Some ID systems cannot be provided in the content, i. e. some ID systems shall be located outside the content, for example using RDF. |
| --- | --- |
- bib.al.original-language: en
- bib.dp.publication-date: 2025-03-01
- ids.document: 100000012
- ids.tracing: hash-D36E2D61CAD7D9554161EE96001780678489DCDA6EE47EE3350CB5A031B13DDC
- obj.clause-number: B.2
- obj.element-name: paragraph
- obj.language: en
- obj.modality: requirement
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-d02df3cbdc604f6: Initial situation for ID systems, list extract (provision)
| → | Since some requirements are incompatible, no ID system can cover all requirements, so that several ID systems shall be supplied. |
| --- | --- |
- bib.al.original-language: en
- bib.dp.publication-date: 2025-03-01
- ids.document: 100000012
- ids.tracing: hash-6E9E253CAC3FF0DEC9D88F8DA43C09A618799DEA3F83A83E648E6902C14A23F6
- obj.clause-number: B.2
- obj.element-name: paragraph
- obj.language: en
- obj.modality: requirement
- obj.normativity: informative
- obj.specobject-type: provision
- use.business-process: undefined
- use.business-sector: undefined
- use.interaction: undefined
- use.location: undefined
- use.product-category: undefined
- use.product-life-cycle: undefined
- use.project-phase: undefined
- use.purpose: undefined

### R643: Challenges regarding multiple ID systems (heading)
- bib.al.original-language: en
- bib.dp.publication-date: 2025-03-01
- ids.document: 100000012
- obj.clause-number: B.3
- obj.element-name: heading
- obj.language: en
- obj.specobject-type: heading
- ChapterName: B.3 Challenges regarding multiple ID systems

#### prov-100000012-4bb04b185b5e400: Challenges regarding multiple ID systems (provision)
- The involved partners should only operate as many ID systems as are minimally necessary so that the processes remain manageable.
- The involved partners should not discard already established ID systems if this would jeopardize the operation of ongoing processes.
- bib.al.original-language: en
- bib.dp.publication-date: 2025-03-01
- ids.document: 100000012
- ids.tracing: hash-AF52486045E9F91D802A4AEA4C6295FC87BB18AD0161165DE0776FFE3362204C
- obj.clause-number: B.3
- obj.element-name: unordered-list
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-64c6d3c40fc04a9: Challenges regarding multiple ID systems, list extract (provision)
| → | The involved partners should only operate as many ID systems as are minimally necessary so that the processes remain manageable. |
| --- | --- |
- bib.al.original-language: en
- bib.dp.publication-date: 2025-03-01
- ids.document: 100000012
- ids.tracing: hash-770801A7DAE06969CF7B6A8B52DA2C65FBED5A3AD951960F47A6157C7D243081
- obj.clause-number: B.3
- obj.element-name: paragraph
- obj.language: en
- obj.modality: recommendation
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-27d3885fc01b4a6: Challenges regarding multiple ID systems, list extract (provision)
| → | The involved partners should not discard already established ID systems if this would jeopardize the operation of ongoing processes. |
| --- | --- |
- bib.al.original-language: en
- bib.dp.publication-date: 2025-03-01
- ids.document: 100000012
- ids.tracing: hash-5AB106B65A33741D74A13F3279E05E084F5D19FCAA2B53DBC4E376CEE0CB1BE4
- obj.clause-number: B.3
- obj.element-name: paragraph
- obj.language: en
- obj.modality: recommendation
- obj.normativity: informative
- obj.specobject-type: provision
- use.business-process: undefined
- use.business-sector: undefined
- use.interaction: undefined
- use.location: undefined
- use.product-category: undefined
- use.product-life-cycle: undefined
- use.project-phase: undefined
- use.purpose: undefined

### R647: Recommendations for maintaining multiple ID systems (heading)
- bib.al.original-language: en
- bib.dp.publication-date: 2025-03-01
- ids.document: 100000012
- obj.clause-number: B.4
- obj.element-name: heading
- obj.language: en
- obj.specobject-type: heading
- ChapterName: B.4 Recommendations for maintaining multiple ID systems

#### prov-100000012-56f89ea94485401: Recommendations for maintaining multiple ID systems (provision)
- The involved partners should identify and minimize redundant ID systems, provided this does not jeopardize the operation of ongoing processes.
- The involved partners should identify and harmonize incompatible ID systems, provided this does not jeopardize the operation of ongoing processes.
- bib.al.original-language: en
- bib.dp.publication-date: 2025-03-01
- ids.document: 100000012
- ids.tracing: hash-121EB7A7C961D24BCFB5BD060A784800C2700B07D13B2CFA5629B198042894F4
- obj.clause-number: B.4
- obj.element-name: unordered-list
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-48e4502ce6bd4c1: Recommendations for maintaining multiple ID systems, list extract (provision)
| → | The involved partners should identify and minimize redundant ID systems, provided this does not jeopardize the operation of ongoing processes. |
| --- | --- |
- bib.al.original-language: en
- bib.dp.publication-date: 2025-03-01
- ids.document: 100000012
- ids.tracing: hash-D53F696E3726AAC54280994EFF59D0343D155B9022B227F307A08831FA89474F
- obj.clause-number: B.4
- obj.element-name: paragraph
- obj.language: en
- obj.modality: recommendation
- obj.normativity: informative
- obj.specobject-type: provision
- use.business-process: undefined
- use.business-sector: undefined
- use.interaction: undefined
- use.location: undefined
- use.product-category: undefined
- use.product-life-cycle: undefined
- use.project-phase: undefined
- use.purpose: undefined

##### prov-100000012-22042ae6b489456: Recommendations for maintaining multiple ID systems, list extract (provision)
| → | The involved partners should identify and harmonize incompatible ID systems, provided this does not jeopardize the operation of ongoing processes. |
| --- | --- |
- bib.al.original-language: en
- bib.dp.publication-date: 2025-03-01
- ids.document: 100000012
- ids.tracing: hash-45F4A0D7421C93486614E29E3E08005306673F70D57A68595AC10D8897CE46FF
- obj.clause-number: B.4
- obj.element-name: paragraph
- obj.language: en
- obj.modality: recommendation
- obj.normativity: informative
- obj.specobject-type: provision
- use.business-process: undefined
- use.business-sector: undefined
- use.interaction: undefined
- use.location: undefined
- use.product-category: undefined
- use.product-life-cycle: undefined
- use.project-phase: undefined
- use.purpose: undefined

## R651: Determination of the normativity (obj.normativity) (heading)
- bib.al.original-language: en
- bib.dp.publication-date: 2025-03-01
- ids.document: 100000012
- obj.clause-number: Annex C
- obj.element-name: heading
- obj.language: en
- obj.specobject-type: heading
- ChapterName: Annex C Determination of the normativity (obj.normativity)

### prov-100000012-ec444f9e4e2343a: Determination of the normativity (obj.normativity) (provision)
If the source document is an XML instance, the value of the attribute obj.normativity (8.2.1.2) can be determined as follows:
- bib.al.original-language: en
- bib.dp.publication-date: 2025-03-01
- ids.document: 100000012
- ids.tracing: hash-06E8218D8315D496A8A75E6EF547E0A1B408237B3E607082573E06B4A90B9DDD
- obj.clause-number: Annex C
- obj.element-name: paragraph
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R124

### prov-100000012-cae15d313a274ba: Determination of the normativity (obj.normativity) (provision)
| informative context | normative context |
| --- | --- |
| The value is “informative” if the context of the current element is: - bibliographic annex; - informative appendix; - example; - footnote; - note; - preface; - introduction; - metadata; profile data (title page); - any other verified informative context. | The value is “normative” if the context of the current element is not an informative context. |
- bib.al.original-language: en
- bib.dp.publication-date: 2025-03-01
- ids.document: 100000012
- ids.tracing: hash-01C6F44EDCCA0EDF80D59D601597D651484D113ED023F6516A68CE8920412610
- obj.clause-number: Annex C
- obj.element-name: document
- obj.language: en
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-100000012-67ca2bcee83a434: Determination of the normativity (obj.normativity) (provision)
The suppliers should optimize the implemented method during their continuous improvement process.
- bib.al.original-language: en
- bib.dp.publication-date: 2025-03-01
- ids.document: 100000012
- ids.tracing: hash-1C4797671C06BAC12E89A912CE608074A1F75C87AB014BC051CD94BA6204A682
- obj.clause-number: Annex C
- obj.element-name: paragraph
- obj.language: en
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

#### prov-100000012-7d2e70692dba411: Determination of the normativity (obj.normativity), Note (provision)
NOTE:
This method has the advantage, that in case of a mismatch the risk is lower to review a false-classified normative content instead of missing a normative content.
- bib.al.original-language: en
- bib.dp.publication-date: 2025-03-01
- ids.document: 100000012
- ids.tracing: hash-D5C3EABCFB6ABD83ADCEA36A50017FC67448A06D6C5A8D1D1F622A819FD2F654
- obj.clause-number: Annex C
- obj.element-name: note
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

## R656: Determination of the conversion reliability (obj.conversion-reliability) (heading)
- bib.al.original-language: en
- bib.dp.publication-date: 2025-03-01
- ids.document: 100000012
- obj.clause-number: Annex D
- obj.element-name: heading
- obj.language: en
- obj.specobject-type: heading
- ChapterName: Annex D Determination of the conversion reliability (obj.conversion-reliability)

### prov-100000012-d737c5e8d27046b: Determination of the conversion reliability (obj.conversion-reliability) (provision)
If the source document is an XML instance, the value of the attribute obj.conversion-reliability (8.2.1.2) can be determined the occurrences of:
- words in a sentence;
- “and”;
- “not”;
- “or”;
- “shall” and “have to” (requirement);
- “should” and “ought” (recommendation);
- “may” and “can” (capability or possibility);
- “must” (external constraint);
- “is” or “are”;
- “de:soll” or “de:sollen” (ambiguous and therefore deprecated);
- infinitives, for example “to carry out” or “to check”;
- “accordingly”, “or”, or “respectively”;
- “for example”, “e. g.”, or “e.g.”;
- “and so forth”, “and so on”, “et cetera”, or “etc.”.
- bib.al.original-language: en
- bib.dp.publication-date: 2025-03-01
- ids.document: 100000012
- ids.tracing: hash-95DD722FA7A3BADAC5EDB34E0568A9DE90CEDB22D65F14538A5F24C843FB5D22
- obj.clause-number: Annex D
- obj.element-name: paragraph
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> R124

### prov-100000012-e86c7953fe0a4ad: Determination of the conversion reliability (obj.conversion-reliability) (provision)
The suppliers should optimize the implemented method during their continuous improvement process.
- bib.al.original-language: en
- bib.dp.publication-date: 2025-03-01
- ids.document: 100000012
- ids.tracing: hash-57DC5B7A0666F926A37B6C6DF7AEEEE69C8C6EA29EA3869894CFAA23F68DCDA7
- obj.clause-number: Annex D
- obj.element-name: paragraph
- obj.language: en
- obj.modality: recommendation
- obj.normativity: informative
- obj.specobject-type: provision
- use.business-process: undefined
- use.business-sector: undefined
- use.interaction: undefined
- use.location: undefined
- use.product-category: undefined
- use.product-life-cycle: undefined
- use.project-phase: undefined
- use.purpose: undefined

## R659: Bibliography (heading)
- bib.al.original-language: en
- bib.dp.publication-date: 2025-03-01
- ids.document: 100000012
- obj.element-name: heading
- obj.language: en
- obj.specobject-type: heading

### prov-100000012-996957e8ccc24fe: Bibliography (provision)
- 1
ISO/IEC 9834-8:2014, Information technology – Procedures for the operation of object identifier registration authorities – Part 8: Generation of universally unique identifiers (UUIDs) and their use in object identifiers
- 2
ISO/IEC 10646, Information technology – Universal coded character set (UCS)
- 3
ISO 12639, Graphic technology – Prepress digital data exchange – Tag image file format for image technology (TIFF/IT)
- 4
ISO/IEC 15948, Information technology – Computer graphics and image processing – Portable Network Graphics (PNG): Functional specification
- 5
ISO/IEC 19757-3, Information technology – Document Schema Definition Languages (DSDL) – Part 3: Rule-based validation using Schematron
- 6
ISO/IEC Guide 2, Standardization and related activities – General vocabulary
- 7
Scenarios for Digitizing Standardization and Standards – Whitepaper 1. IDiS Initiative for Digital Standards (DIN, DKE): Berlin, Offenbach, 2021-06
- 8
Use Cases for SMART Standards – Whitepaper 2. IDiS Initiative for Digital Standards (DIN, DKE): Berlin, Offenbach, 2022-05
- 9
Porter, Michael E. Competitive Advantage: Creating and Sustaining Superior Performance. California: Free Press, 1985.
- 10
A Universally Unique IDentifier (UUID) URN Namespace. Network Working Group, 2005-07. Internet: https://datatracker.ietf.org/doc/html/rfc4122/
- 11
Memorandum of Understanding Between W3C and WHATWG. W3C, 2019-05-28. Internet: https://www.w3.org/2019/04/WHATWG-W3C-MOU.html
- bib.al.original-language: en
- bib.dp.publication-date: 2025-03-01
- ids.document: 100000012
- ids.tracing: hash-D94B1C436AFF0FB08D570BD3268DBC87A54E4EB54B0884FB82CAF0C7E6FF6692
- obj.element-name: list-of-documents
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

## prov-100000012-385597a8805640c: Bibliographic document metadata (provision)
a Metadata Field Specification
- bib.al.original-language: en
- bib.dp.publication-date: 2025-03-01
- ids.document: 100000012
- ids.tracing: hash-FE37310DC604B600DFEEAB7F6598ACBF63DBAA80B6E6EED708F262C663F77410
- obj.clause-number: Table 4
- obj.element-name: footnote
- obj.language: en
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
