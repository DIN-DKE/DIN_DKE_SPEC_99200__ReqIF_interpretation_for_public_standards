# DIN VDE 0132 (VDE 0132):2018-07

# Specification: DIN VDE 0132 (VDE 0132):2018-07
- bib.ca.classification: ICS_13.220.10
- bib.dp.publication-date: 2018-07-01
- bib.rx.replaced-by: E DIN VDE 0132 (VDE 0132):2025-08
- bib.rz.replaces: DIN VDE 0132 (VDE 0132):2015-10
- bib.tf.title-french: Lutte contre l’incendie et secours technique dans ou prés des installations électriques
- bib.tg.title-german: Brandbekämpfung und technische Hilfeleistung im Bereich elektrischer Anlagen
- bib.ti.title-english: Firefighting and technical assistance in or near electrical installations
- bib.ts.document-type: WN
- ids.document: 7104561
- pub.software: VDE CaaS 1.5.15
- pub.supplier: VDE
- pub.transformation-date: 2025-06-23T14:21:16.107673548Z

## pkn--7104561: Lutte contre l’incendie et secours technique dans ou prés des installations électriques (document)
DIN VDE 0132 (VDE 0132):2018-07
- bib.al.original-language: de
- bib.ca.classification: ICS_13.220.10
- bib.dp.publication-date: 2018-07-01
- bib.rx.replaced-by: E DIN VDE 0132 (VDE 0132):2025-08
- bib.rz.replaces: DIN VDE 0132 (VDE 0132):2015-10
- bib.tg.title-german: Brandbekämpfung und technische Hilfeleistung im Bereich elektrischer Anlagen
- bib.ti.title-english: Firefighting and technical assistance in or near electrical installations
- bib.ts.document-type: WN
- ids.document: 7104561
- obj.language: de
- obj.specobject-type: document
- pub.harmonization: IDiS ReqIF interpretation for public standards 1.3
- pub.originator: DKE
- pub.sales-number: 0100473
- pub.software: VDE CaaS 1.5.15
- pub.supplier: VDE
- pub.transformation-date: 2025-06-23T14:21:16.107673548Z
- pub.url: https://[changeme].dke.de/api/publications/7104561/reqif

## R2 (heading)
- bib.al.original-language: de
- bib.dp.publication-date: 2018-07-01
- ids.document: 7104561
- obj.element-name: heading
- obj.language: de
- obj.specobject-type: heading

### prov-7104561-d412308778cb459 (provision)
|  |  |  | DIN VDE 0132 (VDE 0132) |  |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 |  |  |
| --- | --- | --- | --- | --- | --- | --- | --- |
|  |  |  | Diese Norm ist zugleich eine VDE-Bestimmung im Sinne von VDE 0022. Sie ist nach Durchführung des vom VDE-Präsidium beschlossenen Genehmigungsverfahrens unter der oben angeführten Nummer in das VDE-Vorschriftenwerk aufgenommen und in der „etz Elektrotechnik + Automation“ bekannt gegeben worden. |  |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 |  |  |
| Vervielfältigung – auch für innerbetriebliche Zwecke – nicht gestattet. |  |  |  |  |  |  |  |
|  |  | ICS 13.220.10 |  | Ersatz für DIN VDE 0132 (VDE 0132):2015-10 Siehe Anwendungsbeginn |  |  |  |
|  | Brandbekämpfung und technische Hilfeleistung im Bereich elektrischer Anlagen Firefighting and technical assistance in or near electrical installations Lutte contre l’incendie et secours technique dans ou prés des installations électriques |  |  |  |  |  |  |
|  | Gesamtumfang 28 Seiten DKE Deutsche Kommission Elektrotechnik Elektronik Informationstechnik in DIN und VDE |  |  |  |  |  |  |
| © DIN Deutsches Institut für Normung e. V. und VDE Verband der Elektrotechnik Elektronik Informationstechnik e. V. Jede Art der Vervielfältigung, auch auszugsweise, nur mit Genehmigung des DIN, Berlin, und des VDE, Frankfurt am Main, gestattet. Einzelverkauf und Abonnements durch VDE VERLAG GMBH, 10625 Berlin Einzelverkauf auch durch Beuth Verlag GmbH, 10772 Berlin |  |  |  |  |  | Preisgr. 19 K VDE-Vertr.-Nr. 0100473 |  |
- bib.al.original-language: de
- bib.dp.publication-date: 2018-07-01
- ids.document: 7104561
- ids.tracing: hash-E246C134A30D8A569E5CBB1FAFC6FE44BE72AA8AB583BFA2B2CACB4D8B6AC5B2
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> pkn--7061874

## R4: Anwendungsbeginn (heading)
- bib.al.original-language: de
- bib.dp.publication-date: 2018-07-01
- ids.document: 7104561
- obj.element-name: heading
- obj.language: de
- obj.specobject-type: heading

### prov-7104561-7d748233ad6a450: Anwendungsbeginn (provision)
Anwendungsbeginn dieser Norm ist 2018-07-01.
- bib.al.original-language: de
- bib.dp.publication-date: 2018-07-01
- ids.document: 7104561
- ids.tracing: hash-FE93CA57B7193C689487EF31CCE5E627ECAE5D1A35FA5B35C9DE9EF97C360513
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-a832d2b087e9419: Anwendungsbeginn (provision)
Für DIN VDE 0132 (VDE 0132):2015-10 besteht eine Übergangsfrist bis 2021-06-30.
- bib.al.original-language: de
- bib.dp.publication-date: 2018-07-01
- ids.document: 7104561
- ids.tracing: hash-AACC5856D3BA1C15B8DB864AEE663B2609508F961D9560FDDD5777AD7BC55B6E
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> pkn--7061874

## R7: Vorwort (heading)
- bib.al.original-language: de
- bib.dp.publication-date: 2018-07-01
- ids.document: 7104561
- obj.element-name: heading
- obj.language: de
- obj.specobject-type: heading

### prov-7104561-6d13586d2e33443: Vorwort (provision)
Vorausgegangener Norm-Entwurf: E DIN VDE 0132 (VDE 0132):2017-04.
- bib.al.original-language: de
- bib.dp.publication-date: 2018-07-01
- ids.document: 7104561
- ids.tracing: hash-CEA8DD3D5E201D261330303573BD4028EE417D9E0618804CB1281D00B12048AA
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-d66dba8faf0f4f3: Vorwort (provision)
Für diese Norm ist das nationale Arbeitsgremium K 213 „Brandbekämpfung in elektrischen Anlagen“ der DKE Deutsche Kommission Elektrotechnik Elektronik Informationstechnik in DIN und VDE (www.dke.de) zuständig.
- bib.al.original-language: de
- bib.dp.publication-date: 2018-07-01
- ids.document: 7104561
- ids.tracing: hash-872057849D9807B6A5B60F6B9AC4070B8E4675955226BB7BC7D2579E03588B8B
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-0fbbb82950154e3: Vorwort (provision)
Diese Norm regelt das Verhalten und die Verwendung von Geräten für die Brandbekämpfung und technische Hilfeleistung in elektrischen Anlagen und in deren Nähe.
- bib.al.original-language: de
- bib.dp.publication-date: 2018-07-01
- ids.document: 7104561
- ids.tracing: hash-2C069074FC94BB807C9C556586E2DAC542660E2CC7D54DD5938F224DEDA9E67A
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-8ed62563b37b4ba: Vorwort (provision)
Zudem kann diese Norm dem Anwender Hilfestellung bei der Erstellung der Gefährdungsbeurteilung nach der Betriebsicherheitsverordnung bzw. der DGUV Vorschrift 1 „Grundsätze der Prävention“ geben.
- bib.al.original-language: de
- bib.dp.publication-date: 2018-07-01
- ids.document: 7104561
- ids.tracing: hash-622C3995861C4D08033C124C085B8FD8579644E29013E12669D5D3291DD41EA3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-d1e08a560b6a474: Vorwort (provision)
Es wird auf die Möglichkeit hingewiesen, dass einige Elemente dieses Dokuments Patentrechte berühren können.
- bib.al.original-language: de
- bib.dp.publication-date: 2018-07-01
- ids.document: 7104561
- ids.tracing: hash-135AAD218C5687D9233721F1E0B17540E78938365A4C5C9C996DE8E1F1F2A7AB
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-d966227863da4a9: Vorwort (provision)
DIN und DKE sind nicht dafür verantwortlich, einige oder alle diesbezüglichen Patentrechte zu identifizieren.
- bib.al.original-language: de
- bib.dp.publication-date: 2018-07-01
- ids.document: 7104561
- ids.tracing: hash-12AA78511D003BFDCCCBA118FDCBFBCCD19FBD764B1F4C1E97D82969EA296D58
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### R14: Änderungen (heading)
- bib.al.original-language: de
- bib.dp.publication-date: 2018-07-01
- ids.document: 7104561
- obj.element-name: heading
- obj.language: de
- obj.specobject-type: heading

#### prov-7104561-5f24e91f08ee46d: Änderungen (provision)
Gegenüber DIN VDE 0132 (VDE 0132):2015-10 wurden folgende Änderungen vorgenommen:
- a) 5.1.3 "Maßnahmen bei Überflutung zur Sicherstellung der Personensicherheit" redaktionell geändert;
- b) 5.1.5 "Besondere Maßnahmen bei Lithium-Ionen-Akkumulatoren" neu aufgenommen.
- bib.al.original-language: de
- bib.dp.publication-date: 2018-07-01
- ids.document: 7104561
- ids.tracing: hash-A5471565F4FC0CCFCE85444843BE4C3ECDC31DAE8D0E219268CF7BB65CF023DA
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R130
- cross-reference -> R156
- cross-reference -> pkn--7061874

### R16: Frühere Ausgaben (heading)
- bib.al.original-language: de
- bib.dp.publication-date: 2018-07-01
- ids.document: 7104561
- obj.element-name: heading
- obj.language: de
- obj.specobject-type: heading

#### prov-7104561-9779ec1b1da14e0: Frühere Ausgaben (provision)
DIN VDE 0132 (VDE 0132): 1979-02, 1989-11 , 2001-08 , 2008-08 , 2012-08 , 2015-10
- bib.al.original-language: de
- bib.dp.publication-date: 2018-07-01
- ids.document: 7104561
- ids.tracing: hash-541C93FCE3A6913A5DB4155A2B821E23C547A1D5D09D2AE7477123AB4F47BDB7
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

## R18: Anwendungsbereich (heading)
- bib.al.original-language: de
- bib.dp.publication-date: 2018-07-01
- ids.document: 7104561
- obj.clause-number: 1
- obj.element-name: heading
- obj.language: de
- obj.specobject-type: heading
- ChapterName: 1 Anwendungsbereich

### prov-7104561-afdb2535e7aa414: Anwendungsbereich (provision)
Diese Norm dient zur Unterrichtung der Personen, die für die Brandbekämpfung und technische Hilfeleistung in elektrischen Anlagen und in deren Nähe zuständig sind.
- bib.al.original-language: de
- bib.dp.publication-date: 2018-07-01
- ids.document: 7104561
- ids.tracing: hash-BB4F5782777F2B58DB42DB6D09ADB5597A8A6F24815FD50AA6F54E0B7A9DF90A
- obj.clause-number: 1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-c349943ed6984ef: Anwendungsbereich (provision)
Die in dieser Norm angegebenen Werte der Mindestabstände für Annäherung und Löschmitteleinsatz gelten nicht für Anlagen mit Nennspannungen bis AC 50 V (Wechselspannung) / DC 120 V (Gleichspannung).
- bib.al.original-language: de
- bib.dp.publication-date: 2018-07-01
- ids.document: 7104561
- ids.tracing: hash-896DD60D5C8B9280E028F5E9B5F3132C1166E71616F873D201D3F6C08C6D44FE
- obj.clause-number: 1
- obj.element-name: paragraph
- obj.language: de
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-0885ed979b364a2: Anwendungsbereich (provision)
Die Norm gilt nicht für die Errichtung und den Betrieb ortsfester Löschanlagen, für Beregnungsanlagen, Wasserwerfer und dergleichen sowie für besondere Löschmaßnahmen, wie z. B. das Fluten von Kabelkanälen mit Wasser oder Schaum.
- bib.al.original-language: de
- bib.dp.publication-date: 2018-07-01
- ids.document: 7104561
- ids.tracing: hash-1006FC2E040F08EDDAA16D4B6F68C83A3EBAF9A01C19E5DAEED81CD68101ED7C
- obj.clause-number: 1
- obj.element-name: paragraph
- obj.language: de
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-c2cd3bfbb29648b: Anwendungsbereich (provision)
Diese Norm gilt auch für die Verwendung von Strahlrohren nach DIN 14365-1:1991-02 und DIN 14365-2:1986-09, die nicht europäisch genormt sind, sofern diese noch im Einsatz sind.
- bib.al.original-language: de
- bib.dp.publication-date: 2018-07-01
- ids.document: 7104561
- ids.tracing: hash-EB60F7A709B83AAD69872A706E8AC7FEF26D3E3BFCBD53AB3100660AB102D66D
- obj.clause-number: 1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

## R23: Normative Verweisungen (heading)
- bib.al.original-language: de
- bib.dp.publication-date: 2018-07-01
- ids.document: 7104561
- obj.clause-number: 2
- obj.element-name: heading
- obj.language: de
- obj.specobject-type: heading
- ChapterName: 2 Normative Verweisungen

### prov-7104561-252087cdfc274f6: Normative Verweisungen (provision)
Die folgenden Dokumente, die in diesem Dokument teilweise oder als Ganzes zitiert werden, sind für die Anwendung dieses Dokuments erforderlich.
- bib.al.original-language: de
- bib.dp.publication-date: 2018-07-01
- ids.document: 7104561
- ids.tracing: hash-09D55A084D9C0CE9E10C2D6282D5CC3497E794DE5DAA49A4AEDB6ECA9F9DCC9E
- obj.clause-number: 2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-6e2db9b256e446f: Normative Verweisungen (provision)
Bei datierten Verweisungen gilt nur die in Bezug genommene Ausgabe.
- bib.al.original-language: de
- bib.dp.publication-date: 2018-07-01
- ids.document: 7104561
- ids.tracing: hash-EC5B0D96310FFFE3F327D7CF895455CF1704B0AAFDC238EBDACF4C93B879E474
- obj.clause-number: 2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-df85116f8727424: Normative Verweisungen (provision)
Bei undatierten Verweisungen gilt die letzte Ausgabe des in Bezug genommenen Dokuments (einschließlich aller Änderungen).
- DIN 14095, Feuerwehrpläne für bauliche Anlagen ^1)
- DIN 14365-1:1991-02, Mehrzweckstrahlrohre PN 16 – Maße, Werkstoffe, Ausführung, Kennzeichnung
- DIN 14365-2:1986-09, Mehrzweckstrahlrohre PN 16 – Anforderungen, Prüfung^1)
- DIN 14366-2:1984-10, Schaumstrahlrohre für Werfer-Unterteile^1)
- DIN EN 2:2005-01, Brandklassen; Deutsche Fassung EN 2:1992 + A1:2004
- DIN EN 3-7:2007-10, Tragbare Feuerlöscher – Teil 7: Eigenschaften, Leistungsanforderungen und Prüfungen; Deutsche Fassung EN 3-7:2004 + A1:2007
- DIN EN 615:2009-08, Brandschutz – Löschmittel – Anforderungen an Löschpulver (nicht für Löschpulver der Brandklasse D); Deutsche Fassung EN 615:2009
- DIN EN 1568 (alle Teile), Feuerlöschmittel – Schaummittel
- DIN EN 15182-1:2010-04, Strahlrohre für die Brandbekämpfung – Teil 1: Allgemeine Anforderungen; Deutsche Fassung EN 15182-1:2007 + A1:2009
- DIN EN 15182-2:2010-04, Strahlrohre für die Brandbekämpfung – Teil 2: Hohlstrahlrohre PN 16; Deutsche Fassung EN 5182-2:2007 + A1:2009
- DIN EN 15182-3:2010-04, Strahlrohre für die Brandbekämpfung – Teil 3: Strahlrohre mit Vollstrahl und/oder einem unveränderlichen Sprühstrahlwinkel PN 16; Deutsche Fassung EN 15182-3:2007 + A1:2009
- DIN EN 15182-4:2010-04, Strahlrohre für die Brandbekämpfung – Teil 4: Hochdruckstrahlrohre PN 40; Deutsche Fassung EN 15182-4:2007 + A1:2009
- DIN EN 15767-3:2010-12, Tragbare Geräte zum Ausbringen von Löschmitteln, welche mit Feuerlöschpumpen gefördert werden – Tragbare Werfer – Teil 3: Schaumdüsen; Deutsche Fassung EN 15767-3:2010
- DIN EN 16327:2014-07, Feuerwehrwesen – Druckzumischanlagen (DZA) und Druckluftschaumanlagen (DLS); Deutsche Fassung EN 16327:2014
- DIN EN 16712-3:2015-12, Tragbare Geräte zum Ausbringen von Löschmitteln, die mit Feuerlöschpumpen gefördert werden – Tragbare Schaumgeräte – Teil 3: Schwer- und Mittelschaumrohre PN 16; Deutsche Fassung EN°16712-3:2015
- DIN EN 50122-1 (VDE 0115-3):2017-10 , Bahnanwendungen – Ortsfeste Anlagen – Elektrische Sicherheit, Erdung und Rückleitung – Teil 1: Schutzmaßnahmen gegen elektrischen Schlag; Deutsche Fassung EN 50122-1:2011 + A1:2011 + AC:2012 + AC:2016 + A3:2016 + A4:2017
- DIN EN 62040-1 (VDE 0558-510):2013-11 , Unterbrechungsfreie Stromversorgungssysteme (USV) – Teil 1: Allgemeine Anforderungen und Sicherheitsanforderungen (IEC 62040-1:2008 + Corrigendum September 2008 + A1:2013); Deutsche Fassung EN 62040-1:2008 + Corrigendum Februar 2009 + A1:2013
- DIN VDE 0105-100 (VDE 0105-100):2015-10 , Betrieb von elektrischen Anlagen – Teil 100: Allgemeine Festlegungen
- DIN VDE 0105-103 (VDE 0105-103):2014-10 , Betrieb von elektrischen Anlagen – Zusatzfestlegungen für Bahnen
- E DIN IEC 62335 (VDE 0661-20):2008-08, Ortsveränderliche Fehlerstrom-Schutzeinrichtungen mit geschaltetem Schutzleiter zur Anwendung für Geräte der Schutzklasse I und für batteriebetriebene Fahrzeuge (IEC 23E/632/CDV:2007)
- DIN EN ISO 7010, Graphische Symbole – Sicherheitsfarben und Sicherheitszeichen – Registrierte Sicherheitszeichen
- IEC 60417-DB:2010, Graphische Symbole für Betriebsmittel
- Feuerwehrdienstvorschrift 500, Einheiten im ABC-Einsatz ^2)
- DGUV Information 204-006, Anleitung zur Ersten Hilfe ^3)
- DGUV Fachinformation, 2016-09, Stromunfall - Ärztliche Vorstellung notwendig ^3)
- bib.al.original-language: de
- bib.dp.publication-date: 2018-07-01
- ids.document: 7104561
- ids.tracing: hash-7F7BA27D567E9DA599483698DB1686B86301DBF36551015E50068A4F1EB0A267
- obj.clause-number: 2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> pkn--7095271
- cross-reference -> pkn--7036174
- cross-reference -> pkn
- cross-reference -> pkn--7048005
- cross-reference -> pkn--4020860

#### prov-7104561-7a45e2832a99448: Normative Verweisungen (provision)
1)
Zurückgezogen.
- bib.al.original-language: de
- bib.dp.publication-date: 2018-07-01
- ids.document: 7104561
- ids.tracing: hash-2244D842C89291936C4C024909461A329B43B6FEE342C9BF7875CB4D7D9581A2
- obj.clause-number: 2
- obj.element-name: footnote
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-7104561-ebc47087836d45a: Normative Verweisungen (provision)
2)
Zu beziehen bei: Ausschuss Feuerwehrangelegenheiten, Katastrophenschutz und zivile Verteidigung (AFKzV). Diese Dienstvorschrift wurde vom AFKzV den Ländern zur Einführung empfohlen.
- bib.al.original-language: de
- bib.dp.publication-date: 2018-07-01
- ids.document: 7104561
- ids.tracing: hash-93C75B4E7557E32D87BD7B93C9D8D8F4D91AD1AA81D9E406C26FA3665A315631
- obj.clause-number: 2
- obj.element-name: footnote
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-7104561-f577ae60f247468: Normative Verweisungen (provision)
3)
Zu beziehen bei: DGUV Deutsche Gesetzliche Unfallversicherung.
- bib.al.original-language: de
- bib.dp.publication-date: 2018-07-01
- ids.document: 7104561
- ids.tracing: hash-E7EE866BAF1143819BD053640804595FB42AFDBC12A553137939CA3A7AE88BFA
- obj.clause-number: 2
- obj.element-name: footnote
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-7104561-8d9207967cba450: Normative Verweisungen (provision)
3)
Zu beziehen bei: DGUV Deutsche Gesetzliche Unfallversicherung.
- bib.al.original-language: de
- bib.dp.publication-date: 2018-07-01
- ids.document: 7104561
- ids.tracing: hash-A6BFB5A49DC4E0A7608FC6CEDBD37B6CDDBBC2D365642D2B57BCA62D1B3C3410
- obj.clause-number: 2
- obj.element-name: footnote
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-7104561-42d4f3fe27ef432: Normative Verweisungen (provision)
Zurückgezogen.
- bib.al.original-language: de
- bib.dp.publication-date: 2018-07-01
- ids.document: 7104561
- ids.tracing: hash-15BC0CAB7762D4DECFBAD2391368915CA6B55D3FA9F78DA00FBCE7F74C10CDD9
- obj.clause-number: 2
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-7104561-464d9ceef70c47b: Normative Verweisungen (provision)
Zu beziehen bei: Ausschuss Feuerwehrangelegenheiten, Katastrophenschutz und zivile Verteidigung (AFKzV).
- bib.al.original-language: de
- bib.dp.publication-date: 2018-07-01
- ids.document: 7104561
- ids.tracing: hash-D9EBF3E6D1AF2F6F70E7DFA13EA8656C77A104D63A924C785AD3245709C2F739
- obj.clause-number: 2
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-7104561-926d549ec0fe46c: Normative Verweisungen (provision)
Diese Dienstvorschrift wurde vom AFKzV den Ländern zur Einführung empfohlen.
- bib.al.original-language: de
- bib.dp.publication-date: 2018-07-01
- ids.document: 7104561
- ids.tracing: hash-44A5554D1CD40506D2D077AA9B396211E550988DC52B53FFAD47F03D6C213C98
- obj.clause-number: 2
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-7104561-51e7186a8dfa4c4: Normative Verweisungen (provision)
Zu beziehen bei: DGUV Deutsche Gesetzliche Unfallversicherung.
- bib.al.original-language: de
- bib.dp.publication-date: 2018-07-01
- ids.document: 7104561
- ids.tracing: hash-0286DAC6125C5615F49FAF2B41B7770812873D6B59168EAF797631EF9D8BF12C
- obj.clause-number: 2
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-7104561-bc3bd692526141f: Normative Verweisungen (provision)
Zu beziehen bei: DGUV Deutsche Gesetzliche Unfallversicherung.
- bib.al.original-language: de
- bib.dp.publication-date: 2018-07-01
- ids.document: 7104561
- ids.tracing: hash-FF37B82697EF8F3A5D78796C07C10887BC89515ACE6B8EA5F0D2A505B22EA84B
- obj.clause-number: 2
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

## R36: Begriffe (heading)
- bib.al.original-language: de
- bib.dp.publication-date: 2018-07-01
- ids.document: 7104561
- obj.clause-number: 3
- obj.element-name: heading
- obj.language: de
- obj.specobject-type: heading
- ChapterName: 3 Begriffe

### prov-7104561-361b85b3074c4e9: Begriffe (provision)
Für die Anwendung dieses Dokuments gelten die folgenden Begriffe.
- bib.al.original-language: de
- bib.dp.publication-date: 2018-07-01
- ids.document: 7104561
- ids.tracing: hash-A95D17DB783B63280043F6447E5C9ABC7EB74B66227CD2AE6E84F1BC25455D9F
- obj.clause-number: 3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-87471f9fcd0f46d: abgeschlossene elektrische Betriebsstätte (provision)
3.1
abgeschlossene elektrische Betriebsstätte
Raum oder ein Ort, der ausschließlich zum Betrieb elektrischer Anlagen dient und unter Verschluss gehalten wird. Zutritt haben Elektrofachkräfte und elektrotechnisch unterwiesene Personen, Laien jedoch nur in Begleitung von Elektrofachkräften oder elektrotechnisch unterwiesenen Personen.
Anmerkung 1 zum Begriff: Hierzu gehören z. B. abgeschlossene Schalt- und Verteilungsanlagen, Transformatorzellen, Schaltfelder, Maststationen.
[QUELLE: DIN VDE 0105-100 (VDE 0105-100):2015-10 ]
- bib.al.original-language: de
- bib.dp.publication-date: 2018-07-01
- ids.document: 7104561
- ids.tracing: hash-8FD8A5F732EBDB908F610C68FE4C674AED1D1C22BBBE53B2AF8FE8D1CC189BC5
- obj.clause-number: 3.1
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> pkn

#### prov-7104561-bb04622289d547b: abgeschlossene elektrische Betriebsstätte (provision)
Raum oder ein Ort, der ausschließlich zum Betrieb elektrischer Anlagen dient und unter Verschluss gehalten wird.
- bib.al.original-language: de
- bib.dp.publication-date: 2018-07-01
- ids.document: 7104561
- ids.tracing: hash-E973C915D57E639CDA7308C400D23976B8AD7C3A19C215B00234124A178E5CBD
- obj.clause-number: 3.1
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-2e3f56b358a7426: abgeschlossene elektrische Betriebsstätte (provision)
Zutritt haben Elektrofachkräfte und elektrotechnisch unterwiesene Personen, Laien jedoch nur in Begleitung von Elektrofachkräften oder elektrotechnisch unterwiesenen Personen.
- bib.al.original-language: de
- bib.dp.publication-date: 2018-07-01
- ids.document: 7104561
- ids.tracing: hash-783F248C6ADD95DBCED0559837634B3835569D8FE65EB06154240ABFBB25221B
- obj.clause-number: 3.1
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-bc246b55dc6645d: Anlagenverantwortlicher (provision)
3.2
Anlagenverantwortlicher
eine Person, die beauftragt ist, während der Durchführung von Arbeiten die unmittelbare Verantwortung für den sicheren Betrieb der elektrischen Anlage zu tragen, die zur Arbeitsstelle gehört
Anmerkung 1 zum Begriff: Der Anlagenverantwortliche hat die möglichen Auswirkungen der Arbeiten auf die elektrische Anlage oder die Teile davon, die in seiner Verantwortung stehen, sowie die Auswirkungen der elektrischen Anlage auf die Arbeitsstelle und die arbeitenden Personen zu beurteilen. Erforderlichenfalls können einige mit dieser Verantwortung einhergehende Verpflichtungen auf andere Personen übertragen werden (siehe auch DIN VDE 0105-100 (VDE 0105-100):2015-10, 4.3 ).
[QUELLE: DIN VDE 0105-100 (VDE 0105-100):2015-10 , modifiziert, Anmerkung 2 wurde nicht übernommen.]
- bib.al.original-language: de
- bib.dp.publication-date: 2018-07-01
- ids.document: 7104561
- ids.tracing: hash-6020EAAB537D0D2AEDD9246728487BE0720763F64E832C5353DA37E142396485
- obj.clause-number: 3.2
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> pkn

#### prov-7104561-2d9d3672c46b470: Anlagenverantwortlicher (provision)
eine Person, die beauftragt ist, während der Durchführung von Arbeiten die unmittelbare Verantwortung für den sicheren Betrieb der elektrischen Anlage zu tragen, die zur Arbeitsstelle gehört
- bib.al.original-language: de
- bib.dp.publication-date: 2018-07-01
- ids.document: 7104561
- ids.tracing: hash-ACBD82696C615C7B8CCBF2F29E1633DBC055B07720E3667172D9DA2E85CEAB64
- obj.clause-number: 3.2
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-034488baff1f47e: Anlagenbetreiber (provision)
3.3
Anlagenbetreiber
Person mit der Gesamtverantwortung für den sicheren Betrieb der elektrischen Anlage, die Regeln und Randbedingungen der Organisation vorgibt
Anmerkung 1 zum Begriff: Diese Person kann der Eigentümer, Unternehmer, Besitzer oder eine beauftragte Person sein, die die Unternehmerpflichten wahrnimmt.
Anmerkung 2 zum Begriff: Erforderlichenfalls können einige mit dieser Verantwortung einhergehende Verpflichtungen auf andere Personen übertragen werden. Bei umfangreichen oder komplexen Anlagen kann diese Zuständigkeit auch für Teilanlagen übertragen sein (siehe auch DIN VDE 0105-100 (VDE 0105-100):2015-10, 4.3 ).
[QUELLE: DIN VDE 0105-100 (VDE 0105-100):2015-10 , modifiziert, Anmerkung 3 wurde nicht übernommen.]
- bib.al.original-language: de
- bib.dp.publication-date: 2018-07-01
- ids.document: 7104561
- ids.tracing: hash-064476D7C1C595E6B6F2E3D6FEA10D6C3AF2D23B5BDD24CEF049F6AF42F29A45
- obj.clause-number: 3.3
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> pkn

#### prov-7104561-cf5b4ff24b9546b: Anlagenbetreiber (provision)
Person mit der Gesamtverantwortung für den sicheren Betrieb der elektrischen Anlage, die Regeln und Randbedingungen der Organisation vorgibt
- bib.al.original-language: de
- bib.dp.publication-date: 2018-07-01
- ids.document: 7104561
- ids.tracing: hash-A80970F23B9C286C621795BA9B0DFF8D51C0BA04FCD7FF98E61DF585DE7D65F5
- obj.clause-number: 3.3
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-d145980b837a405: Anlagenbetreiber (provision)
[QUELLE: DIN VDE 0105-100 (VDE 0105-100):2015-10 , modifiziert, Anmerkung 3 wurde nicht übernommen.]
- bib.al.original-language: de
- bib.dp.publication-date: 2018-07-01
- ids.document: 7104561
- ids.tracing: hash-50A21E9B4F2FCA28AE3ABBB9BEFC731D96C368D0D7F135261FBEC22574FF1C22
- obj.clause-number: 3.3
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-e729dc7ac05248f: automatische Brandmeldeanlagen (provision)
3.4
automatische Brandmeldeanlagen
Einrichtungen, die den Zweck haben, Schadenfeuer zum frühestmöglichen Zeitpunkt zu erkennen und so zu melden, dass geeignete Gegenmaßnahmen ergriffen werden können (z. B. Räumung von Gebäuden, Herbeirufen von Löschkräften, selbsttätiges Auslösen von Löschvorgängen, Schließen von Feuerschutzabschlüssen, Steuern von Klima- und Lüftungsanlagen)
- bib.al.original-language: de
- bib.dp.publication-date: 2018-07-01
- ids.document: 7104561
- ids.tracing: hash-E61DFC543A98E45D159DE7EC733D9CCABDB688479716149D977EDE683F3E6394
- obj.clause-number: 3.4
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-d27ecce0189e46e: automatische Brandmeldeanlagen (provision)
Einrichtungen, die den Zweck haben, Schadenfeuer zum frühestmöglichen Zeitpunkt zu erkennen und so zu melden, dass geeignete Gegenmaßnahmen ergriffen werden können (z. B. Räumung von Gebäuden, Herbeirufen von Löschkräften, selbsttätiges Auslösen von Löschvorgängen, Schließen von Feuerschutzabschlüssen, Steuern von Klima- und Lüftungsanlagen)
- bib.al.original-language: de
- bib.dp.publication-date: 2018-07-01
- ids.document: 7104561
- ids.tracing: hash-4953E913BF4239F5507ACE787F97BE517A9E352CC9F6176B99EE954110FC9D2C
- obj.clause-number: 3.4
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-302af75ef06e4fd: Brandklassen (provision)
3.5
Brandklassen
Einteilung von Bränden in Abhängigkeit des Brennstoffes
Anmerkung 1 zum Begriff: Nach DIN EN 2 werden folgende Brandklassen unterschieden.
- bib.al.original-language: de
- bib.dp.publication-date: 2018-07-01
- ids.document: 7104561
- ids.tracing: hash-FF4ABD520738FCB77A997C2BE91EB3EC72FAADFFBC42496D79CC3F14EBBA2A77
- obj.clause-number: 3.5
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-f6f4b9abd0e043a: Brandklassen (provision)
Einteilung von Bränden in Abhängigkeit des Brennstoffes
- bib.al.original-language: de
- bib.dp.publication-date: 2018-07-01
- ids.document: 7104561
- ids.tracing: hash-9F027A1F3FC6F8B7931C96C9789D12881C13A1E5E9EA69A8401659487CDFD7A8
- obj.clause-number: 3.5
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-6ab2c73a57e0478: Brandklasse A (provision)
3.5.1
Brandklasse A
Brände fester Stoffe, hauptsächlich organischer Natur, die normalerweise unter Glutbildung verbrennen, z. B. Holz, Papier, Stroh, Textilien, Kohle
- bib.al.original-language: de
- bib.dp.publication-date: 2018-07-01
- ids.document: 7104561
- ids.tracing: hash-2E3A4D99C11150320067611B93E1FE74D2E5F41101BE5FFC89C292B4BFB27252
- obj.clause-number: 3.5.1
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-ede7dc545e3a496: Brandklasse A (provision)
Brände fester Stoffe, hauptsächlich organischer Natur, die normalerweise unter Glutbildung verbrennen, z. B. Holz, Papier, Stroh, Textilien, Kohle
- bib.al.original-language: de
- bib.dp.publication-date: 2018-07-01
- ids.document: 7104561
- ids.tracing: hash-775BE7EBA3B1C59AE45DC4601BE8286A18739AC5A3075DC96DA8512C7A581043
- obj.clause-number: 3.5.1
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-0e361f89e705463: Brandklasse B (provision)
3.5.2
Brandklasse B
Brände von flüssigen oder flüssig werdenden Stoffen, z. B. Benzin, Benzol, Öle, Fette, Lacke, Teer, Äther, Alkohol, Stearin, Paraffin
- bib.al.original-language: de
- bib.dp.publication-date: 2018-07-01
- ids.document: 7104561
- ids.tracing: hash-C8A7E1F63D8E767659DB96D662A48F5FC394D8284EE8ADB86977EF2CDE8841F3
- obj.clause-number: 3.5.2
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-a5392925ef9348c: Brandklasse B (provision)
Brände von flüssigen oder flüssig werdenden Stoffen, z. B. Benzin, Benzol, Öle, Fette, Lacke, Teer, Äther, Alkohol, Stearin, Paraffin
- bib.al.original-language: de
- bib.dp.publication-date: 2018-07-01
- ids.document: 7104561
- ids.tracing: hash-36055642D20EDEF675E5DAF25C65810E27811C795455CA1D412014B19CD67839
- obj.clause-number: 3.5.2
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-0118f872aae946f: Brandklasse C (provision)
3.5.3
Brandklasse C
Brände von Gasen, z. B. Methan, Propan, Wasserstoff, Acetylen, Erdgas
- bib.al.original-language: de
- bib.dp.publication-date: 2018-07-01
- ids.document: 7104561
- ids.tracing: hash-54DF2D4E35823CAC5D3969269A18A6F31C4CC0C1632D2C72BFE3C732B5881111
- obj.clause-number: 3.5.3
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-cb0fc0206299405: Brandklasse C (provision)
Brände von Gasen, z. B. Methan, Propan, Wasserstoff, Acetylen, Erdgas
- bib.al.original-language: de
- bib.dp.publication-date: 2018-07-01
- ids.document: 7104561
- ids.tracing: hash-C1ABA4E00DF3E6F5150C73446C94B859753144A8C190E142DE8EB1D9DE701772
- obj.clause-number: 3.5.3
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-471e1c0032a1429: Brandklasse D (provision)
3.5.4
Brandklasse D
Brände von Metallen, z. B. Aluminium, Magnesium und ihre Legierungen, Natrium, Kalium
- bib.al.original-language: de
- bib.dp.publication-date: 2018-07-01
- ids.document: 7104561
- ids.tracing: hash-2AA4E5906DBEC68B6F63D015EAB56E90DE1C8B2E3F4F3C258FBB802A04D429FE
- obj.clause-number: 3.5.4
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-6885fbbf1b444f5: Brandklasse D (provision)
Brände von Metallen, z. B. Aluminium, Magnesium und ihre Legierungen, Natrium, Kalium
- bib.al.original-language: de
- bib.dp.publication-date: 2018-07-01
- ids.document: 7104561
- ids.tracing: hash-9CFC3D67294D69F9157A8AB13E49D439451547E601311CBEDF3391015284A4E4
- obj.clause-number: 3.5.4
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-6df6c26bace74a5: Brandklasse F (provision)
3.5.5
Brandklasse F
Brände von Speiseölen/-fetten (pflanzliche oder tierische Öle und Fette) in Frittier- und Fettbackgeräten und anderen Kücheneinrichtungen und -geräten
- bib.al.original-language: de
- bib.dp.publication-date: 2018-07-01
- ids.document: 7104561
- ids.tracing: hash-F759E570A4673D9F44ED418DDD3F8FC593B0CF4E80CB9006C6DA93B89827D915
- obj.clause-number: 3.5.5
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-9fc9862d7a6c4f6: Brandklasse F (provision)
Brände von Speiseölen/-fetten (pflanzliche oder tierische Öle und Fette) in Frittier- und Fettbackgeräten und anderen Kücheneinrichtungen und -geräten
- bib.al.original-language: de
- bib.dp.publication-date: 2018-07-01
- ids.document: 7104561
- ids.tracing: hash-5DC33C203F7247EA871CE10FE9B73F26A9B0BFFAD5F06520ADD5D07B82B23518
- obj.clause-number: 3.5.5
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-ab01431085ef4e6: dezentrale Stromerzeugungsanlagen (provision)
3.6
dezentrale Stromerzeugungsanlagen
Anlagen zur Erzeugung von elektrischem Strom für den Eigenverbrauch und/oder zur Einspeisung in das öffentliche Energieversorgungsnetz
Anmerkung 1 zum Begriff: Dazu gehören z. B. Photovoltaik-Stromversorgungssysteme (PV-Anlagen), Brennstoffzellenanlagen, Windenergieanlagen. Dezentrale Stromerzeugungsanlagen können mit oder ohne elektrische Energiespeicher betrieben werden.
- bib.al.original-language: de
- bib.dp.publication-date: 2018-07-01
- ids.document: 7104561
- ids.tracing: hash-9B0024283BD544EB64CE0F7FEA7D4B4137C1BADA40060D75F72E9D2C1C144325
- obj.clause-number: 3.6
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-4ca4d5e1177a44a: dezentrale Stromerzeugungsanlagen (provision)
Anlagen zur Erzeugung von elektrischem Strom für den Eigenverbrauch und/oder zur Einspeisung in das öffentliche Energieversorgungsnetz
- bib.al.original-language: de
- bib.dp.publication-date: 2018-07-01
- ids.document: 7104561
- ids.tracing: hash-F2FAF684264A99D9E093EE83E9D032E99BC63B4A7A48CA61D743D908E27186E7
- obj.clause-number: 3.6
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-5d0156f91670491: Druckluftschaum (en: compressed air foam) (provision)
3.7
Druckluftschaum (en: compressed air foam)
Löschschaum, erzeugt durch eine Druckluftschaumanlage
Anmerkung 1 zum Begriff: Druckluftschaumanlagen sind in DIN EN 16327 definiert.
- bib.al.original-language: de
- bib.dp.publication-date: 2018-07-01
- ids.document: 7104561
- ids.tracing: hash-C17B65D987A3E05F65E74287273A672BB0E9BEE002A2066EB8DDD2E3E60E3522
- obj.clause-number: 3.7
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-d4d0f46c5a7f46a: Druckluftschaum (en: compressed air foam) (provision)
Löschschaum, erzeugt durch eine Druckluftschaumanlage
- bib.al.original-language: de
- bib.dp.publication-date: 2018-07-01
- ids.document: 7104561
- ids.tracing: hash-E82841635DFD094257A90085D9D1BCFA75BF8A73F1C51CBB471119906E27C791
- obj.clause-number: 3.7
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-53aa6c8e914f421 (provision)
3.8
elektrische Anlage
Anlagen mit elektrischen Betriebsmitteln zur Erzeugung, Übertragung, Umwandlung, Verteilung und Anwendung elektrischer Energie
Den elektrischen Betriebsmitteln gleichgesetzt werden Werkzeuge, Ausrüstungen, Schutz- und Hilfsmittel, soweit an diese Anforderungen hinsichtlich der elektrischen Sicherheit gestellt werden.
Anmerkung 1 zum Begriff: Dies schließt Energiequellen ein wie Batterien, Kondensatoren und alle anderen Quellen gespeicherter elektrischer Energie.
[QUELLE: DIN VDE 0105-100 (VDE 0105-100):2015-10 ]
- bib.al.original-language: de
- bib.dp.publication-date: 2018-07-01
- ids.document: 7104561
- ids.tracing: hash-AE3BC4F8FC5C60118A3BD35AB186C33AB6E1242B335E98FA0AD1DA068F766FDE
- obj.clause-number: 3.8
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-f31a1247496d473 (provision)
Anlagen mit elektrischen Betriebsmitteln zur Erzeugung, Übertragung, Umwandlung, Verteilung und Anwendung elektrischer Energie
- bib.al.original-language: de
- bib.dp.publication-date: 2018-07-01
- ids.document: 7104561
- ids.tracing: hash-FFA55EBBC283E7D1E728B58C30EC31EF02F7C1595DE186DDC7813F7FF790740D
- obj.clause-number: 3.8
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-34914255b50d4fe (provision)
Den elektrischen Betriebsmitteln gleichgesetzt werden Werkzeuge, Ausrüstungen, Schutz- und Hilfsmittel, soweit an diese Anforderungen hinsichtlich der elektrischen Sicherheit gestellt werden.
- bib.al.original-language: de
- bib.dp.publication-date: 2018-07-01
- ids.document: 7104561
- ids.tracing: hash-A031D090326E9C65CB48BA88951408D292044814D94E50D77D1042B8808E39CE
- obj.clause-number: 3.8
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-9626f3186bd64c6 (provision)
Anmerkung 1 zum Begriff: Dies schließt Energiequellen ein wie Batterien, Kondensatoren und alle anderen Quellen gespeicherter elektrischer Energie.
- bib.al.original-language: de
- bib.dp.publication-date: 2018-07-01
- ids.document: 7104561
- ids.tracing: hash-6C40F21D49D35C8343D97DD14CA7848E5C29657A5BCB2E71304ABCB944191017
- obj.clause-number: 3.8
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-f8787ad1c11a4bd (provision)
[QUELLE: DIN VDE 0105-100 (VDE 0105-100):2015-10 ]
- bib.al.original-language: de
- bib.dp.publication-date: 2018-07-01
- ids.document: 7104561
- ids.tracing: hash-769C6F9C7E9FEB45A0CB0D9F658F4793EE9ACB973E0E03FC44D8B113EF832A21
- obj.clause-number: 3.8
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> pkn

### prov-7104561-eb22e42d014b474: Elektrofachkraft (provision)
3.9
Elektrofachkraft
ist, wer aufgrund seiner fachlichen Ausbildung, Kenntnisse und Erfahrungen sowie Kenntnis der einschlägigen Normen die ihm übertragenen Arbeiten beurteilen und mögliche Gefahren erkennen kann
Anmerkung 1 zum Begriff: Zur Beurteilung der fachlichen Ausbildung kann auch eine mehrjährige Tätigkeit auf dem betreffenden Arbeitsgebiet herangezogen werden.
[QUELLE: DIN VDE 0105-100 (VDE 0105-100):2015-10 ]
- bib.al.original-language: de
- bib.dp.publication-date: 2018-07-01
- ids.document: 7104561
- ids.tracing: hash-079A56C1E067CB7BC10FA2B3B59500390B10A8916B247816D330268BE3097F53
- obj.clause-number: 3.9
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> pkn

#### prov-7104561-76c0bbba82a8462: Elektrofachkraft (provision)
ist, wer aufgrund seiner fachlichen Ausbildung, Kenntnisse und Erfahrungen sowie Kenntnis der einschlägigen Normen die ihm übertragenen Arbeiten beurteilen und mögliche Gefahren erkennen kann
- bib.al.original-language: de
- bib.dp.publication-date: 2018-07-01
- ids.document: 7104561
- ids.tracing: hash-0DB38A4B3FD0619EA3A1C09BCF62C03AF2F11D9D777607A915F98826490969C1
- obj.clause-number: 3.9
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-d5437d5f04fc42c: elektrotechnisch unterwiesene Person (provision)
3.10
elektrotechnisch unterwiesene Person
ist, wer durch eine Elektrofachkraft über die ihr übertragenen Aufgaben und die möglichen Gefahren bei unsachgemäßem Verhalten unterrichtet und erforderlichenfalls angelernt sowie über die notwendigen Schutzeinrichtungen und Schutzmaßnahmen unterwiesen wurde
[QUELLE: DIN VDE 0105-100 (VDE 0105-100):2015-10 ]
- bib.al.original-language: de
- bib.dp.publication-date: 2018-07-01
- ids.document: 7104561
- ids.tracing: hash-220DE6B5CE330F112EDF8635A96A7D2028E47141C10510819B85BE779F43AE23
- obj.clause-number: 3.10
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> pkn

#### prov-7104561-637a14912bb94c7: elektrotechnisch unterwiesene Person (provision)
ist, wer durch eine Elektrofachkraft über die ihr übertragenen Aufgaben und die möglichen Gefahren bei unsachgemäßem Verhalten unterrichtet und erforderlichenfalls angelernt sowie über die notwendigen Schutzeinrichtungen und Schutzmaßnahmen unterwiesen wurde
[QUELLE: DIN VDE 0105-100 (VDE 0105-100):2015-10 ]
- bib.al.original-language: de
- bib.dp.publication-date: 2018-07-01
- ids.document: 7104561
- ids.tracing: hash-5804FB66669D8CA3669E763E940F82D243CA461188A5A08C57FF3EEE27A0FD19
- obj.clause-number: 3.10
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-d67463fba4e14d0: fahrbare Feuerlöscher (provision)
3.11
fahrbare Feuerlöscher
fahrbare Feuerlöschgeräte ohne eigenen Kraftantrieb
- bib.al.original-language: de
- bib.dp.publication-date: 2018-07-01
- ids.document: 7104561
- ids.tracing: hash-3A214AFC054F3B089B3D6E00FE84F04E1675208F6A143E84353A961F0F32CFAD
- obj.clause-number: 3.11
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-93fb45066e8a495: fahrbare Feuerlöscher (provision)
fahrbare Feuerlöschgeräte ohne eigenen Kraftantrieb
- bib.al.original-language: de
- bib.dp.publication-date: 2018-07-01
- ids.document: 7104561
- ids.tracing: hash-33D9ACE117A0296A9EC1A17CE07FE1DE4EB56CFD4F8E2B0968CADF70E5387116
- obj.clause-number: 3.11
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-96953cc8e3df4e9 (provision)
3.12
Fahrleitung
Leitersystem zur Versorgung von Fahrzeugen mit elektrischer Energie über Stromabnahmeeinrichtungen
Anmerkung 1 zum Begriff: Es umfasst alle Leiter, die zur Stromabnahme nötig sind, sowie Stromschienen und beinhaltet Folgendes:
- Verstärkungsleitungen,
- Schalterquerleitungen,
- Trennschalter,
- Streckentrenner,
- Überspannungsschutzeinrichtungen,
- Trageinrichtungen, die nicht von den Leitern isoliert sind,
- Isolatoren, die mit aktiven Teilen verbunden sind.
Nicht zur Fahrleitung gehören:
- Speiseleitungen,
- Erdseile und Rückleiter.
[QUELLE: DIN EN 50122-1 (VDE 0115-3):2017-10 ]
- bib.al.original-language: de
- bib.dp.publication-date: 2018-07-01
- ids.document: 7104561
- ids.tracing: hash-B4812254D8D383765777987ED6EFCDFF9721E8A88494BD0A4A38A8626A1F0EC3
- obj.clause-number: 3.12
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-83fe68dbe779444 (provision)
Leitersystem zur Versorgung von Fahrzeugen mit elektrischer Energie über Stromabnahmeeinrichtungen
- bib.al.original-language: de
- bib.dp.publication-date: 2018-07-01
- ids.document: 7104561
- ids.tracing: hash-EB2C9D20781DF1F6DD752162B6BEBCD2611F21CB93C66FD00DFC12A0B4DFE3AA
- obj.clause-number: 3.12
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-92b74463bfa6495 (provision)
Anmerkung 1 zum Begriff: Es umfasst alle Leiter, die zur Stromabnahme nötig sind, sowie Stromschienen und beinhaltet Folgendes:
- Verstärkungsleitungen,
- Schalterquerleitungen,
- Trennschalter,
- Streckentrenner,
- Überspannungsschutzeinrichtungen,
- Trageinrichtungen, die nicht von den Leitern isoliert sind,
- Isolatoren, die mit aktiven Teilen verbunden sind.
- bib.al.original-language: de
- bib.dp.publication-date: 2018-07-01
- ids.document: 7104561
- ids.tracing: hash-995B0B865457C4C792F407FB8FD7999A36C9E3FBC8E6189232F2BA3B61962347
- obj.clause-number: 3.12
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-318b81bc20d54ae (provision)
Nicht zur Fahrleitung gehören:
- Speiseleitungen,
- Erdseile und Rückleiter.
- bib.al.original-language: de
- bib.dp.publication-date: 2018-07-01
- ids.document: 7104561
- ids.tracing: hash-BB1DFB880D4659E740D6ADF3FD6D26911691A3FB0CBC069DF5BE504EA78FE5C5
- obj.clause-number: 3.12
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-fc4fc1d3d5c5403 (provision)
[QUELLE: DIN EN 50122-1 (VDE 0115-3):2017-10 ]
- bib.al.original-language: de
- bib.dp.publication-date: 2018-07-01
- ids.document: 7104561
- ids.tracing: hash-5D0B75F9412BE720099DE2825873901BB13B3FD3D71D88AB7723BFB110E50C2C
- obj.clause-number: 3.12
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> pkn--7095271

### prov-7104561-fd991a4cc73746f: Freileitung (provision)
3.13
Freileitung
elektrische Leitung, deren Leiter oberirdisch geführt sind, im Allgemeinen mit Hilfe von Isolatoren und geeigneten Stützpunkten
Anmerkung 1 zum Begriff: Bestimmte Freileitungen können mit isolierten Leitern ausgerüstet sein.
[QUELLE: IEV 466-01-02]
- bib.al.original-language: de
- bib.dp.publication-date: 2018-07-01
- ids.document: 7104561
- ids.tracing: hash-6C4B535D14B27BE51EF59C6483EF93E6F651E17F88E641913CFEBAB6517C44FD
- obj.clause-number: 3.13
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-0ad617d8c6a3442: Freileitung (provision)
elektrische Leitung, deren Leiter oberirdisch geführt sind, im Allgemeinen mit Hilfe von Isolatoren und geeigneten Stützpunkten
- bib.al.original-language: de
- bib.dp.publication-date: 2018-07-01
- ids.document: 7104561
- ids.tracing: hash-855E92405AB990C53ED77E12DA305036BE80FAF35B4AD5BD5047C678C28785AF
- obj.clause-number: 3.13
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-2da2c2f556d9461: Hochvolt HV (provision)
3.14
Hochvolt HV
Spannungen oberhalb von AC 25 V oder DC 60 V in Elektrofahrzeugen
Anmerkung 1 zum Begriff: Dies schließt Fahrzeuge mit Hybridantrieben und Fahrzeuge mit Brennstoffzellenantrieben ein.
- bib.al.original-language: de
- bib.dp.publication-date: 2018-07-01
- ids.document: 7104561
- ids.tracing: hash-2B58951A6CBCA03F8A055FC4BAA7780A46826A230A30067E4DAAD86A41DE9C6A
- obj.clause-number: 3.14
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-11997139afdc4df: Hochvolt HV (provision)
Spannungen oberhalb von AC 25 V oder DC 60 V in Elektrofahrzeugen
- bib.al.original-language: de
- bib.dp.publication-date: 2018-07-01
- ids.document: 7104561
- ids.tracing: hash-21EE1D7B1B78376CEF4A1F78042B13794FBF2467B672E6ECED8152F78EAACF9F
- obj.clause-number: 3.14
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-ed71785c485e45a: Hochspannungsanlage (provision)
3.15
Hochspannungsanlage
elektrische Anlage, die mit einer Nennspannung größer AC 1 000 V (Wechselspannung) oder DC 1 500 V (Gleichspannung) betrieben wird
Anmerkung 1 zum Begriff: Zu den Hochspannungsanlagen gehören insbesondere Anlagen, die der Stromerzeugung oder der Umwandlung, Verteilung und Anwendung elektrischer Energie dienen, z. B. Kraftwerke, Schalt- und Umspannanlagen, Freileitungen, Kabelanlagen sowie Anlagen und Fahrzeuge von elektrischen Bahnen.
Anmerkung 2 zum Begriff: Hochspannungsanlagen – mit Ausnahme von Freileitungen und Fahrleitungen elektrischer Bahnen – sind in der Regel durch das Warnschild W012 „Warnung vor elektrischer Spannung“ nach DIN EN ISO 7010 oder Warnschild „gefährliche Spannung“ nach IEC 60417-5036 gekennzeichnet.
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Anmerkung 3 zum Begriff:
- bib.al.original-language: de
- bib.dp.publication-date: 2018-07-01
- ids.document: 7104561
- ids.tracing: hash-1634F1E32B63ADC1706D33A8C8D4722B2B8A4DAFB97F72B5D314ED8EDFB3669F
- obj.clause-number: 3.15
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-247e2e4c91f240f: Hochspannungsanlage (provision)
elektrische Anlage, die mit einer Nennspannung größer AC 1 000 V (Wechselspannung) oder DC 1 500 V (Gleichspannung) betrieben wird
- bib.al.original-language: de
- bib.dp.publication-date: 2018-07-01
- ids.document: 7104561
- ids.tracing: hash-D2C13DD29246DC3B7D555500E062958E67627A0F0B7CFFA32994A37AB04CB10F
- obj.clause-number: 3.15
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-1d7cdf44533a4e6: Niederspannungsanlage (provision)
3.16
Niederspannungsanlage
elektrische Anlage, die mit einer Nennspannung kleiner oder gleich AC 1 000 V (Wechselspannung) oder DC 1 500 V (Gleichspannung) betrieben wird
Anmerkung 1 zum Begriff: Zu den Niederspannungsanlagen gehören z. B. Stromerzeugungs- und Verteilungsanlagen, Ortsnetze, Hausinstallationen sowie Installationen für industrielle, gewerbliche und landwirtschaftliche Betriebe, die Fahrleitungen und Installationen der mit Gleichspannung (Niederspannung) betriebenen Straßen- und Stadtbahnen, Oberleitungsbusse (Obusse), Fernmelde- und Informationsverarbeitungsanlagen.
- bib.al.original-language: de
- bib.dp.publication-date: 2018-07-01
- ids.document: 7104561
- ids.tracing: hash-8A594A6C6DC42731E55809494919E57EA4D6D73521FD421A2A41CCDC4E722875
- obj.clause-number: 3.16
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-89a229e0b35748e: Niederspannungsanlage (provision)
elektrische Anlage, die mit einer Nennspannung kleiner oder gleich AC 1 000 V (Wechselspannung) oder DC 1 500 V (Gleichspannung) betrieben wird
- bib.al.original-language: de
- bib.dp.publication-date: 2018-07-01
- ids.document: 7104561
- ids.tracing: hash-1251DC0E7B96A1C3A417F9296DEACB0932471B948CA2A2EF39F79300D35D303E
- obj.clause-number: 3.16
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-7f5b9e9fd6974a1: ortsfeste Löschanlagen (provision)
3.17
ortsfeste Löschanlagen
fest installierte Löscheinrichtungen, deren Auslösung von Hand und/oder automatisch erfolgt
- bib.al.original-language: de
- bib.dp.publication-date: 2018-07-01
- ids.document: 7104561
- ids.tracing: hash-6585C815B9F58A09D11EE7FCE250321C711B2C1B20E7C6F26D04FE68050E1A3C
- obj.clause-number: 3.17
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-672dd7d7221b44c: ortsfeste Löschanlagen (provision)
fest installierte Löscheinrichtungen, deren Auslösung von Hand und/oder automatisch erfolgt
- bib.al.original-language: de
- bib.dp.publication-date: 2018-07-01
- ids.document: 7104561
- ids.tracing: hash-9A1ACFF120D53721C50FE22234374A9B76CBDD5E05D2DFD3851AF58D658834C1
- obj.clause-number: 3.17
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-bb7ab81a359548a: SPE-PRCD (provision)
3.18
SPE-PRCD
Differenzstromeinrichtung mit Fehlerstrom-, Schutzleiterbruch-, Schutzleiterspannungs- und Fremdspannungsüberwachung
[QUELLE: E DIN IEC 62335 (VDE 0661-20):2008-06]
- bib.al.original-language: de
- bib.dp.publication-date: 2018-07-01
- ids.document: 7104561
- ids.tracing: hash-61F081931948317715F19F1AFDA18B43206E9CC861C4EA95E4D13E08AA39A543
- obj.clause-number: 3.18
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-5b8e86988c444d0: SPE-PRCD (provision)
Differenzstromeinrichtung mit Fehlerstrom-, Schutzleiterbruch-, Schutzleiterspannungs- und Fremdspannungsüberwachung
- bib.al.original-language: de
- bib.dp.publication-date: 2018-07-01
- ids.document: 7104561
- ids.tracing: hash-BE78BA453CFC1442DA456D5497598881B6750623FAE8DE8B6E2913BE11FE476B
- obj.clause-number: 3.18
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-68e2ef955a3b424: SPE-PRCD (provision)
[QUELLE: E DIN IEC 62335 (VDE 0661-20):2008-06]
- bib.al.original-language: de
- bib.dp.publication-date: 2018-07-01
- ids.document: 7104561
- ids.tracing: hash-6E69407ED44708557B7DC1D71B5A74E73F06D80B812D194B7A897E6B4441F87D
- obj.clause-number: 3.18
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-d00c38bee6564c0: Strahlrohr (provision)
3.19
Strahlrohr
Armaturen zur Abgabe von Löschmitteln
- bib.al.original-language: de
- bib.dp.publication-date: 2018-07-01
- ids.document: 7104561
- ids.tracing: hash-34C61DCC4BD681747558EAA3521358FD37A6CFFA8B279CDE2C4C0F93CF4A71EB
- obj.clause-number: 3.19
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-a397d8e9e762486: Strahlrohr (provision)
Armaturen zur Abgabe von Löschmitteln
- bib.al.original-language: de
- bib.dp.publication-date: 2018-07-01
- ids.document: 7104561
- ids.tracing: hash-030CE09D75EFA4D476BEC993BB80DA24773ADD44385B83B9DF95E732078F7E60
- obj.clause-number: 3.19
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-523ae53802cd466: anderes Strahlrohr (provision)
3.19.1
anderes Strahlrohr
Strahlrohr, das weder Mehrzweckstrahlrohr noch Hohlstrahlrohr ist
- bib.al.original-language: de
- bib.dp.publication-date: 2018-07-01
- ids.document: 7104561
- ids.tracing: hash-14B57E7D102194102D4D1DA6196977A567FB3032B66DFAA4E92C99AB2FDFBF17
- obj.clause-number: 3.19.1
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-9ec35e571871401: anderes Strahlrohr (provision)
Strahlrohr, das weder Mehrzweckstrahlrohr noch Hohlstrahlrohr ist
- bib.al.original-language: de
- bib.dp.publication-date: 2018-07-01
- ids.document: 7104561
- ids.tracing: hash-8C2AE9F8F9C14F7F8291F3CC3175D00008EAAE539A44216D5106ADC74102FD45
- obj.clause-number: 3.19.1
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-ce452401e808483: Hohlstrahlrohr (provision)
3.19.2
Hohlstrahlrohr
Strahlrohr einschließlich einer Schließvorrichtung und einer einstellbaren Strahlform
[QUELLE: DIN EN 15182-2:2010-04, 3.1, verändert übernommen]
- bib.al.original-language: de
- bib.dp.publication-date: 2018-07-01
- ids.document: 7104561
- ids.tracing: hash-4EE4C109B881F73C247F7EBFD37C3B5413C07BBE5E797C4F27C5470D4EA7D202
- obj.clause-number: 3.19.2
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-a97a65406d11451: Hohlstrahlrohr (provision)
Strahlrohr einschließlich einer Schließvorrichtung und einer einstellbaren Strahlform
[QUELLE: DIN EN 15182-2:2010-04, 3.1, verändert übernommen]
- bib.al.original-language: de
- bib.dp.publication-date: 2018-07-01
- ids.document: 7104561
- ids.tracing: hash-2A06CCDD4A35B95163BAF648358BC8C495CFEB204F4D41D8EB34D0898A43ACF6
- obj.clause-number: 3.19.2
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-784459f1d4564d7: Mehrzweckstrahlrohr (provision)
3.19.3
Mehrzweckstrahlrohr
Das Mehrzweckstrahlrohr ist eine Armatur zur gezielten Abgabe vornehmlich von Löschwasser in Form eines Voll- oder Sprühstrahls
Anmerkung 1 zum Begriff: Strahlrohre CM haben einen Mundstückdurchmesser von 9 mm und einen Düsendurchmesser von 12 mm.
Anmerkung 2 zum Begriff: Strahlrohre BM haben einen Mundstückdurchmesser von 16 mm und einen Düsendurchmesser von 22 mm.
[QUELLE: DIN 14365-1:1991-02]
- bib.al.original-language: de
- bib.dp.publication-date: 2018-07-01
- ids.document: 7104561
- ids.tracing: hash-877BCECA58E0B72FCB5C5507D5AEFA842ABB79E8098A5D7C2F722D4941C66797
- obj.clause-number: 3.19.3
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-cef48a8526d4472: Mehrzweckstrahlrohr (provision)
Das Mehrzweckstrahlrohr ist eine Armatur zur gezielten Abgabe vornehmlich von Löschwasser in Form eines Voll- oder Sprühstrahls
- bib.al.original-language: de
- bib.dp.publication-date: 2018-07-01
- ids.document: 7104561
- ids.tracing: hash-08C5C19598F569B364D1847F113E378D1E0BFA3257DC14BB02BE2E84116A55A0
- obj.clause-number: 3.19.3
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-2f5a3f0f28d8485: Mehrzweckstrahlrohr (provision)
[QUELLE: DIN 14365-1:1991-02]
- bib.al.original-language: de
- bib.dp.publication-date: 2018-07-01
- ids.document: 7104561
- ids.tracing: hash-6E6C5FFCE059C05D509A9159F2B3C2FE1EEACAE1349F6D8C25F6ED8E17AEFC32
- obj.clause-number: 3.19.3
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-051d7a050a5a49a: tragbarer Feuerlöscher (provision)
3.20
tragbarer Feuerlöscher
Feuerlöscher, der getragen und von Hand bedient werden kann und im betriebsbereiten Zustand eine Masse von nicht mehr als 20 kg hat
[QUELLE: DIN EN 3-7:2007-10]
- bib.al.original-language: de
- bib.dp.publication-date: 2018-07-01
- ids.document: 7104561
- ids.tracing: hash-F97E8BE8920D9EBB534D9AFF29709E406DB2E9FF10FB6D9976E0CCBDCF627071
- obj.clause-number: 3.20
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-1b88b424598d4f3: tragbarer Feuerlöscher (provision)
Feuerlöscher, der getragen und von Hand bedient werden kann und im betriebsbereiten Zustand eine Masse von nicht mehr als 20 kg hat
[QUELLE: DIN EN 3-7:2007-10]
- bib.al.original-language: de
- bib.dp.publication-date: 2018-07-01
- ids.document: 7104561
- ids.tracing: hash-52A43E8878E2B4DB4E13FB361A8D28D1EAD53C9FE5B6FF245CB1B060D16AB819
- obj.clause-number: 3.20
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-ecc64cb60d8e4d1 (provision)
3.21
trockener Raum
Raum oder bestimmter Bereich innerhalb eines Raums, in dem in der Regel kein Kondenswasser auftritt oder in dem die Luft nicht mit Feuchtigkeit gesättigt ist
Anmerkung 1 zum Begriff: Hierzu gehören z. B. Wohnräume (auch Hotelzimmer), Büros; weiterhin können hierzu gehören:
- Geschäftsräume, Verkaufsräume, Dachböden, Treppenhäuser, beheizte oder belüftbare Keller;
- Küchen in Wohnungen und Baderäume in Wohnungen und Hotels gelten in Bezug auf die Installation als trockene Räume, da in ihnen nur zeitweise Feuchtigkeit auftritt.
- bib.al.original-language: de
- bib.dp.publication-date: 2018-07-01
- ids.document: 7104561
- ids.tracing: hash-881B83230EED3635A61A3F642E310A511494E8A413FA3F75FE4BE07876195B59
- obj.clause-number: 3.21
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-89c8d86f4ffe4b6 (provision)
Raum oder bestimmter Bereich innerhalb eines Raums, in dem in der Regel kein Kondenswasser auftritt oder in dem die Luft nicht mit Feuchtigkeit gesättigt ist
- bib.al.original-language: de
- bib.dp.publication-date: 2018-07-01
- ids.document: 7104561
- ids.tracing: hash-4E2AAFD782B53747424EEDBD968CD81BAC71D66E208D665DDBFC151B4AD4A603
- obj.clause-number: 3.21
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-07aac742fb994ef (provision)
Anmerkung 1 zum Begriff: Hierzu gehören z. B. Wohnräume (auch Hotelzimmer), Büros; weiterhin können hierzu gehören:
- Geschäftsräume, Verkaufsräume, Dachböden, Treppenhäuser, beheizte oder belüftbare Keller;
- Küchen in Wohnungen und Baderäume in Wohnungen und Hotels gelten in Bezug auf die Installation als trockene Räume, da in ihnen nur zeitweise Feuchtigkeit auftritt.
- bib.al.original-language: de
- bib.dp.publication-date: 2018-07-01
- ids.document: 7104561
- ids.tracing: hash-BD0171EE9A76543A47FAD8E2D74D06B5F9DA45BF9B26B5DD0A6625ED4304B96B
- obj.clause-number: 3.21
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### prov-7104561-016a9b7a09e4466: unterbrechungsfreies Stromversorgungssystem USV (provision)
3.22
unterbrechungsfreies Stromversorgungssystem USV
Kombination von Stromrichtern, Schaltern und Energiespeichern (wie Batterien), die ein Stromversorgungssystem bildet, das bei Ausfall der Eingangsversorgung eine beständige Versorgung der Last sicherstellt
[QUELLE: DIN EN 62040-1 (VDE 0558-510):2009-06 ]
- bib.al.original-language: de
- bib.dp.publication-date: 2018-07-01
- ids.document: 7104561
- ids.tracing: hash-5720750E8575F250C4B3E826F4F85A562C97E6A605BF6C8C0BBE44CB92754F38
- obj.clause-number: 3.22
- obj.element-name: concept
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> pkn--3020662

#### prov-7104561-56afd0998448409: unterbrechungsfreies Stromversorgungssystem USV (provision)
Kombination von Stromrichtern, Schaltern und Energiespeichern (wie Batterien), die ein Stromversorgungssystem bildet, das bei Ausfall der Eingangsversorgung eine beständige Versorgung der Last sicherstellt
[QUELLE: DIN EN 62040-1 (VDE 0558-510):2009-06 ]
- bib.al.original-language: de
- bib.dp.publication-date: 2018-07-01
- ids.document: 7104561
- ids.tracing: hash-C0E2C20CF9565DD647B5664EA27CB312161DB0DAC3D9F3BA6CDB97B0014F82EE
- obj.clause-number: 3.22
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

## R109: Vorbereitende Maßnahmen (heading)
- bib.al.original-language: de
- bib.dp.publication-date: 2018-07-01
- ids.document: 7104561
- obj.clause-number: 4
- obj.element-name: heading
- obj.language: de
- obj.specobject-type: heading
- ChapterName: 4 Vorbereitende Maßnahmen

### R110: 4.1 (heading)
- bib.al.original-language: de
- bib.dp.publication-date: 2018-07-01
- ids.document: 7104561
- obj.element-name: heading
- obj.language: de
- obj.specobject-type: heading

#### prov-7104561-86abd70ca1db430 (provision)
Verständnisvolle Zusammenarbeit zwischen Feuerwehr und dem Anlagenbetreiber elektrischer Anlagen ist anzustreben.
- bib.al.original-language: de
- bib.dp.publication-date: 2018-07-01
- ids.document: 7104561
- ids.tracing: hash-131F1176236013533D8AE9D2F656A19593ED12695D2A27B9B5C94A1B8B2E3EC3
- obj.clause-number: 4.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-c1945426fc75477 (provision)
Diesem Zweck dienen unter anderem die Absprachen zwischen Feuerwehr und Anlagenbetreiber über die im Einsatz notwendigen Maßnahmen nach 4.2 bis 4.5.
- bib.al.original-language: de
- bib.dp.publication-date: 2018-07-01
- ids.document: 7104561
- ids.tracing: hash-E30F3FF1BEDBDC3B471EA6755C3A29FFF2D6B38DB6445A07F593832546CE1D08
- obj.clause-number: 4.1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R113

### R113: 4.2 (heading)
- bib.al.original-language: de
- bib.dp.publication-date: 2018-07-01
- ids.document: 7104561
- obj.element-name: heading
- obj.language: de
- obj.specobject-type: heading

#### prov-7104561-6fc92c80779e401 (provision)
Der Anlagenbetreiber gibt der Feuerwehr Aufklärung über besondere Gefährdungen und Schwierigkeiten, die bei Brandbekämpfung und bei technischer Hilfeleistung auftreten können.
- bib.al.original-language: de
- bib.dp.publication-date: 2018-07-01
- ids.document: 7104561
- ids.tracing: hash-CF418E1C7F75F98E70A3B0F1B9015D0B26A193F40E021AAEEF2C5B0B1233C08E
- obj.clause-number: 4.2
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-5c6812bd81034e2 (provision)
Grundlage können Feuerwehrpläne nach DIN 14095 sein, die der raschen Orientierung und der Beurteilung der Lage dienen.
- bib.al.original-language: de
- bib.dp.publication-date: 2018-07-01
- ids.document: 7104561
- ids.tracing: hash-98E58ADFF5185467D23D125B23F63FA2CA47699900AE93E264017E8967EC9C27
- obj.clause-number: 4.2
- obj.element-name: paragraph
- obj.language: de
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

### R116: 4.3 (heading)
- bib.al.original-language: de
- bib.dp.publication-date: 2018-07-01
- ids.document: 7104561
- obj.element-name: heading
- obj.language: de
- obj.specobject-type: heading

#### prov-7104561-a0711b151e34448 (provision)
Isolier-/Kühl-Flüssigkeiten und -Gase können besondere Gefährdungen darstellen.
- bib.al.original-language: de
- bib.dp.publication-date: 2018-07-01
- ids.document: 7104561
- ids.tracing: hash-A8D8D4F4B3AFE00D70BEC607EEFC0313FA21F61B46D3F87ECD680876FEB24C4A
- obj.clause-number: 4.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-ec2a2edfcd3c4fc (provision)
Einschlägige bundes- und landesrechtliche Festlegungen sind zu beachten.
- bib.al.original-language: de
- bib.dp.publication-date: 2018-07-01
- ids.document: 7104561
- ids.tracing: hash-323F739266CEDE040EDBA98EE4ABE0B4755CD96948C43F68F55C39C6776E0C8C
- obj.clause-number: 4.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-28276395737b4ac: , Note (provision)
ANMERKUNG 1:
PCB-haltige elektrische Betriebsmittel sind vom Anlagenbetreiber durch Schilder augenfällig gekennzeichnet.
ANMERKUNG 2 Siehe Anhang A „Beurteilung von Gefahren, die von PCB-haltigen Betriebsmitteln ausgehen können.
- bib.al.original-language: de
- bib.dp.publication-date: 2018-07-01
- ids.document: 7104561
- ids.tracing: hash-C331025136B0E00452300ED4FBBA567CDCA7DFAB483DD31F7F2F83397F26372E
- obj.clause-number: 4.3
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> R318

### R120: 4.4 (heading)
- bib.al.original-language: de
- bib.dp.publication-date: 2018-07-01
- ids.document: 7104561
- obj.element-name: heading
- obj.language: de
- obj.specobject-type: heading

#### prov-7104561-06cea0512f804b6 (provision)
Den Einsatz einer Werkfeuerwehr und die Einsatzleitung bestimmen landesrechtliche Vorschriften.
- bib.al.original-language: de
- bib.dp.publication-date: 2018-07-01
- ids.document: 7104561
- ids.tracing: hash-EDDEC6A8F74D32BC8F41FAB34828036B09A746B7EF6BF4FB8D40F708BE174088
- obj.clause-number: 4.4
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### R122: 4.5 (heading)
- bib.al.original-language: de
- bib.dp.publication-date: 2018-07-01
- ids.document: 7104561
- obj.element-name: heading
- obj.language: de
- obj.specobject-type: heading

#### prov-7104561-46c7536c837d447 (provision)
Der Anlagenbetreiber von Hochspannungsanlagen bezeichnet die Stelle oder nennt Personen, die bei Bränden und technischer Hilfeleistung für den Kontakt mit der Feuerwehr zuständig sind, und gibt die in Frage kommenden Kommunikationsmöglichkeiten bekannt.
- bib.al.original-language: de
- bib.dp.publication-date: 2018-07-01
- ids.document: 7104561
- ids.tracing: hash-39691BF334712CCB9DF650EF08C572DDA6E0A5FEFE8804D2356A7A64194DBDBA
- obj.clause-number: 4.5
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

## R124: Maßnahmen bei Bränden und technischen Hilfeleistungen (heading)
- bib.al.original-language: de
- bib.dp.publication-date: 2018-07-01
- ids.document: 7104561
- obj.clause-number: 5
- obj.element-name: heading
- obj.language: de
- obj.specobject-type: heading
- ChapterName: 5 Maßnahmen bei Bränden und technischen Hilfeleistungen

### R125: Allgemeine Maßnahmen (heading)
- bib.al.original-language: de
- bib.dp.publication-date: 2018-07-01
- ids.document: 7104561
- obj.clause-number: 5.1
- obj.element-name: heading
- obj.language: de
- obj.specobject-type: heading
- ChapterName: 5.1 Allgemeine Maßnahmen

#### R126: 5.1.1 (heading)
- bib.al.original-language: de
- bib.dp.publication-date: 2018-07-01
- ids.document: 7104561
- obj.element-name: heading
- obj.language: de
- obj.specobject-type: heading

##### prov-7104561-9c36f5223b7c429 (provision)
Feuerwehr und Anlagenbetreiber verständigen sich im Brandfall und bei technischer Hilfeleistung entsprechend den getroffenen Vereinbarungen gegenseitig.
- bib.al.original-language: de
- bib.dp.publication-date: 2018-07-01
- ids.document: 7104561
- ids.tracing: hash-079446CFDB9A4B5AD16B7828481314C61B0B7CE410FE590F3A20C3C9A74F1028
- obj.clause-number: 5.1.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### R128: 5.1.2 (heading)
- bib.al.original-language: de
- bib.dp.publication-date: 2018-07-01
- ids.document: 7104561
- obj.element-name: heading
- obj.language: de
- obj.specobject-type: heading

##### prov-7104561-00ff118e9470483 (provision)
Beauftragte des Anlagenbetreibers haben sich auf Anforderung der Feuerwehr zur Verfügung zu stellen und erforderlichenfalls auszuweisen.
- bib.al.original-language: de
- bib.dp.publication-date: 2018-07-01
- ids.document: 7104561
- ids.tracing: hash-2587F819092678AC6404B5863CE346B8191D16EEBBD548820AE206BA9A261440
- obj.clause-number: 5.1.2
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### R130: 5.1.3 (heading)
- bib.al.original-language: de
- bib.dp.publication-date: 2018-07-01
- ids.document: 7104561
- obj.element-name: heading
- obj.language: de
- obj.specobject-type: heading

##### prov-7104561-f605daa50b6c440 (provision)
Maßnahmen bei Überflutung zur Sicherstellung der Personensicherheit.
- bib.al.original-language: de
- bib.dp.publication-date: 2018-07-01
- ids.document: 7104561
- ids.tracing: hash-1EB7E99C035797423253B6C82B4807886B86F3492F8D0335C7BA4BF1544BF6FD
- obj.clause-number: 5.1.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-4dce6eea2fd34a7 (provision)
Durch Überflutungen (z. B. Rohrbrüche, Hochwasser, Löschwasser) können unter Spannung stehende Teile mit Wasser in Berührung kommen und Personen gefährden.
- bib.al.original-language: de
- bib.dp.publication-date: 2018-07-01
- ids.document: 7104561
- ids.tracing: hash-946303260566B5FF2CD1F63C73EA370C6FA70EAB1426CA62540808BF7C28EF3E
- obj.clause-number: 5.1.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-a972837c3bc145c (provision)
Diese Bereiche sind rechtzeitig an sicherer Stelle frei- oder auszuschalten.
- bib.al.original-language: de
- bib.dp.publication-date: 2018-07-01
- ids.document: 7104561
- ids.tracing: hash-572F1AA967779885A0496FFF87BE08D34021209D199DA83F4C78E3091C7488B3
- obj.clause-number: 5.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-b2b3eca51edf4e1 (provision)
Sind elektrische Anlagen bereits überflutet, dürfen diese Bereiche nur nach festgestellter Spannungsfreiheit betreten werden.
- bib.al.original-language: de
- bib.dp.publication-date: 2018-07-01
- ids.document: 7104561
- ids.tracing: hash-093128BD249340D323BD8552599B0A3F20FA4FD5B8526AF8C00D8D529DE2ECCA
- obj.clause-number: 5.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-6d30eea20bec420 (provision)
Der zuständige Netzbetreiber ist zu informieren.
- bib.al.original-language: de
- bib.dp.publication-date: 2018-07-01
- ids.document: 7104561
- ids.tracing: hash-CAB0C4FE5C244B6A32E1C39AF61C5168FAA5C50C7C336897FAE5B9C5F58C239A
- obj.clause-number: 5.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-3ef079ebaf29412 (provision)
Dieser lässt die erforderlichen Freischaltmaßnahmen durchführen oder entscheidet, dass die überfluteten unter Spannung stehenden Anlagen weiter betrieben werden.
- bib.al.original-language: de
- bib.dp.publication-date: 2018-07-01
- ids.document: 7104561
- ids.tracing: hash-B432B9B0310C4F671AE391FF601C610A0C1FE1FCFDBC5483D6FF7D5425453B2F
- obj.clause-number: 5.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-543637ac2c204f4 (provision)
Bei dezentralen Stromerzeugungsanlagen sind die Maßnahmen nach Tabelle 1 anzuwenden.
- bib.al.original-language: de
- bib.dp.publication-date: 2018-07-01
- ids.document: 7104561
- ids.tracing: hash-5958B03F05EC47A95A62A68ACB28DC30343FC0BA8953B59A3E1B7410258A8E6E
- obj.clause-number: 5.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-732b03c7ffc84bc

##### prov-7104561-5babf3c43e6243e (provision)
Die Einheiten der Gefahrenabwehr (z. B. Feuerwehr) setzen nur eigene ortsveränderliche elektrische Betriebsmittel (z. B. Tauchpumpen) ein, die den zu erwartenden Einsatzbedingungen genügen.
- bib.al.original-language: de
- bib.dp.publication-date: 2018-07-01
- ids.document: 7104561
- ids.tracing: hash-7D4158ACC757026B19B8CC2B09B755C8FBF3DC00FF17BC94F08FC10790DD92A8
- obj.clause-number: 5.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-3b5f7c9925cd447 (provision)
Vorrangig sind für die Stromversorgung die eigenen Stromerzeuger einzusetzen.
- bib.al.original-language: de
- bib.dp.publication-date: 2018-07-01
- ids.document: 7104561
- ids.tracing: hash-F075994A1AE12D1513D9B7DFAA5CDD763CE8D9502AF6E8AECF6E0FB734332A48
- obj.clause-number: 5.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-d15bc95af158408 (provision)
Sollte in Ausnahmefällen aufgrund der Einsatzsituation ein anderer Speisepunkt erforderlich sein, darf der Anschluss nur über eine Fehlerstromschutzeinrichtung des Typs SPE-PRCD für den Personenschutz erfolgen.
- bib.al.original-language: de
- bib.dp.publication-date: 2018-07-01
- ids.document: 7104561
- ids.tracing: hash-0F4711FF7B043B7693E4118614B371D8D120BAA715CF923A5CA8D11AF96E823C
- obj.clause-number: 5.1.3
- obj.element-name: paragraph
- obj.language: de
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-8c0c6893590748f (provision)
Dieser ist möglichst nahe an der Stromentnahmestelle zu installieren.
- bib.al.original-language: de
- bib.dp.publication-date: 2018-07-01
- ids.document: 7104561
- ids.tracing: hash-456AA5DC40F6DD8D6E7FF1D4031441825B2826DBB03B1B2F864E5F77E1A57F9F
- obj.clause-number: 5.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### R142: 5.1.4 (heading)
- bib.al.original-language: de
- bib.dp.publication-date: 2018-07-01
- ids.document: 7104561
- obj.element-name: heading
- obj.language: de
- obj.specobject-type: heading

##### prov-7104561-253bba827b6f479 (provision)
Bei Bränden und technischer Hilfeleistung in elektrischen Anlagen (Elektrizitätsversorgungsnetzen und/oder dezentrale Stromversorgungsanlagen) oder in deren Nähe sind, soweit überhaupt eine Notwendigkeit dazu vorliegt, nur die betroffenen oder unmittelbar bedrohten Teile spannungsfrei zu schalten.
- bib.al.original-language: de
- bib.dp.publication-date: 2018-07-01
- ids.document: 7104561
- ids.tracing: hash-E83424BA0C88D8804B2EE111BB7E6C578EBF106E9EE92A1448F37CB4796BFB44
- obj.clause-number: 5.1.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-4021baab36534cf (provision)
Einige Stromversorgungsanlagen können systembedingt nicht spannungsfrei geschaltet werden (siehe Tabelle 1).
- bib.al.original-language: de
- bib.dp.publication-date: 2018-07-01
- ids.document: 7104561
- ids.tracing: hash-D2CAEFBDA43D39A8543CE601C48B7DC0972B44B7712A1E5C5F21057C2CF98F7C
- obj.clause-number: 5.1.4
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-732b03c7ffc84bc

##### prov-7104561-4d3ed96999034a5 (provision)
Grundsatz muss sein, dass so wenig wie möglich ausgeschaltet wird.
- bib.al.original-language: de
- bib.dp.publication-date: 2018-07-01
- ids.document: 7104561
- ids.tracing: hash-78876C42ABF74D2C93DC1AFB178AB3508E50A7C9015716A20E9312CF7F7CF657
- obj.clause-number: 5.1.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-8761d0b7f2394a3 (provision)
Mit Rücksicht auf die Nachteile für die Brandbekämpfung und bei technischer Hilfeleistung sowie für die Allgemeinheit sind Abschaltungen nur in Absprache zwischen Feuerwehr und dem Anlagenbetreiber vorzunehmen.
- bib.al.original-language: de
- bib.dp.publication-date: 2018-07-01
- ids.document: 7104561
- ids.tracing: hash-DA1DEFB81AAFD3370F6CB18B46331D6E583F256BCA34D22BAA3A098CDAB5E40C
- obj.clause-number: 5.1.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-82a096555713422: , Note (provision)
ANMERKUNG 1:
Dadurch soll z. B. vermieden werden:
- bib.al.original-language: de
- bib.dp.publication-date: 2018-07-01
- ids.document: 7104561
- ids.tracing: hash-C8D28035782B404C0CFC5E085A06189F360C053F30697E672E120F28D11F3D83
- obj.clause-number: 5.1.4
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-7104561-9cc1db937ecd471 (provision)
- Gefährdung von Patienten;
- Stilllegen der Wasserversorgung;
- Gefährdungen und Schäden durch die Unterbrechung von Betriebsabläufen;
- Stillstand von Aufzügen und elektrisch betätigten Toren;
- Verdunklung von Straßen.
- bib.al.original-language: de
- bib.dp.publication-date: 2018-07-01
- ids.document: 7104561
- ids.tracing: hash-9283AB733791B50453E9666B231FD06ADEBA545C4EB810030F87A5DDD60924F2
- obj.clause-number: 5.1.4
- obj.element-name: unordered-list
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-d8c93b3671de45a: , Note (provision)
ANMERKUNG 2 Lichtbögen können im Allgemeinen nur durch Ausschalten unterbrochen werden.
- bib.al.original-language: de
- bib.dp.publication-date: 2018-07-01
- ids.document: 7104561
- ids.tracing: hash-5EA4379D530CFC83976A18FF0C3162546C248EECC7560849804FE75C7C932B76
- obj.clause-number: 5.1.4
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-7104561-0fa1c925bc364f4: , Note (provision)
ANMERKUNG 3 Die Benutzung von Aufzügen – mit Ausnahme von Feuerwehraufzügen – ist wegen der Gefahr eines Stromausfalls gefährlich und zu vermeiden.
- bib.al.original-language: de
- bib.dp.publication-date: 2018-07-01
- ids.document: 7104561
- ids.tracing: hash-503C229A2EB5E119866E6886E084E235FF87DBD7179EB77FCC219D1681F6B4D2
- obj.clause-number: 5.1.4
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-7104561-349bc91b1ccf4c1 (provision)
Anlagen, die dem Brandschutz und der Brandbekämpfung dienen (z. B. Rauch- und Wärmeabzugsanlagen, Sprinkler- und Sprühwasserlöschanlagen), dürfen ohne zwingende Notwendigkeit nicht außer Betrieb gesetzt werden.
- bib.al.original-language: de
- bib.dp.publication-date: 2018-07-01
- ids.document: 7104561
- ids.tracing: hash-24262F608D856B38011393C933F97D8901BC8B26FC24B8D4E9FA252F18F3E621
- obj.clause-number: 5.1.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-d563fed4c5ef4a9 (provision)
Durch Schalten elektrischer Betriebsmittel können erhöhte Brand- und Explosionsgefahren auftreten.
- bib.al.original-language: de
- bib.dp.publication-date: 2018-07-01
- ids.document: 7104561
- ids.tracing: hash-0A3CB42566366B9B0C333B44B7848D52DADD2F043EB2B0939C30C0F06F93EDD3
- obj.clause-number: 5.1.4
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-732b03c7ffc84bc: Besonderheiten bei dezentralen Stromerzeugungsanlagen oder anderen Energiesystemen (provision)
Tabelle 1 — Besonderheiten bei dezentralen Stromerzeugungsanlagen oder anderen Energiesystemen
| Energiesystem | Maßnahme | Restgefährdung | Anmerkung |
| --- | --- | --- | --- |
| 1. PV-Anlage | – | Selbst bei durch eine Elektrofachkraft festgestellter Spannungsfreiheit können beim Trennen von Leitungen/Steckverbindern Lichtbögen entstehen. | Trotz Abschaltungen kann nicht von einer vollständigen Spannungsfreiheit der PV-Anlage ausgegangen werden. Daher gilt der Grundsatz Abstand halten. Durch Mondlicht oder künstliches Licht (Scheinwerfer) tritt keine elektrische Gefährdung auf (siehe auch Anhang B „Erläuterungen“). |
| - 2) Elektro- und Hybridfahrzeuge | Deaktivieren des Hochvoltsystems (falls das Rückhaltesystem (z. B. Airbag) ausgelöst hat, ist dies in der Regel sichergestellt). 1. Abklemmen der 12 V/24 V-Batterie oder 2. HV-Wartungsschalter (Service Disconnect) betätigen oder 3. fahrzeugspezifische Trennvorrichtungen betätigen. | Siehe 5.1.5 Besondere Maßnahmen bei Lithium-Ionen-Akkumulatoren. . | Brände können mit Wasser gelöscht werden. Sollten Personen durch technische Hilfeleistung aus dem Fahrzeug zu befreien sein, ist davon auszugehen, dass das Rückhaltesystem ausgelöst hat und das HV-System deaktiviert wurde. HV-Kabel sind orange. HV-Komponenten sind durch das Bildzeichen 5036 nach IEC 60417-DB:2002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 gekennzeichnet. |
| - 3) Batterieanlage (z. B. Sicherheitsstromversorgung, USV-Anlage) | Unter Last dürfen - Sicherungen nicht gezogen und - Kabel/Leitungen nicht gelöst oder getrennt werden. | Spannung bleibt in der eigentlichen Batterieanlage bis zur ersten Abschalt-/ Trennein-richtung bestehen; Gefährdung durch Lichtbogen bei Kurzschluss oder beim Abschalten. | Das Abschalten der Batterie ist nicht möglich. Die von der Batterie versorgte elektrische Anlage kann jedoch in der Regel freigeschaltet werden. |
| - 4) Stromerzeugungsaggregat | Not-Ausschalter betätigen oder Stromerzeuger ausschalten. Zusätzlich Brennstoffzufuhr unterbrechen. | Spannung steht noch bis zum Stillstand des Aggregats an. | – |
| - 5) Brennstoffzellenanlage | Not-Ausschalter betätigen. Zusätzlich Brennstoffzufuhr unterbrechen. | Spannung kann nach Unterbrechen der Brennstoffzufuhr weiter anstehen. | Die Dauer der Restgefährdung ist abhängig von dem dann noch zur Verfügung stehenden Restbrennstoff. |
| - 6) Windenergieanlage | Sicherung der Einsatzstelle, dabei Bauhöhe, Windrichtung und Windstärke berücksichtigen. | Einsturzgefahr, Gefährdung durch wegfliegende Trümmer, Brandausbreitung. | Gegebenenfalls kontrolliert abbrennen lassen. |
- bib.al.original-language: de
- bib.dp.publication-date: 2018-07-01
- ids.document: 7104561
- ids.tracing: hash-42F542C65E01F70A23D42E31B8A30156BD49845D3761192DEBE5CAA562F52269
- obj.clause-number: Tabelle 1
- obj.element-name: table
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R333
- cross-reference -> R156

###### prov-7104561-97c7fa0261d549b: Besonderheiten bei dezentralen Stromerzeugungsanlagen oder anderen Energiesystemen, table extract (provision)
Brandbekämpfung und technische Hilfeleistung sind grundsätzlich möglich, wenn die Abstände nach den Tabellen 2 bis 8 eingehalten werden.
- bib.al.original-language: de
- bib.dp.publication-date: 2018-07-01
- ids.document: 7104561
- ids.tracing: hash-1ED91AD010A93403DC08350D862995E934252ED514C4DCB26261B7D2EAAE40FB
- obj.clause-number: Tabelle 1
- obj.element-name: caption
- obj.language: de
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-b2af74b355cb46d

###### prov-7104561-41d5a44ff09d4d7: Besonderheiten bei dezentralen Stromerzeugungsanlagen oder anderen Energiesystemen, table extract (provision)
Darüber hinaus sind nachstehende Maßnahmen hilfreich.
- bib.al.original-language: de
- bib.dp.publication-date: 2018-07-01
- ids.document: 7104561
- ids.tracing: hash-74E64727A7F12317FB3CAE95A01749172364074C6F607BE482239AF9C3A2D9C2
- obj.clause-number: Tabelle 1
- obj.element-name: caption
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### R156: Besondere Maßnahmen bei Lithium-Ionen-Akkumulatoren (heading)
- bib.al.original-language: de
- bib.dp.publication-date: 2018-07-01
- ids.document: 7104561
- obj.clause-number: 5.1.5
- obj.element-name: heading
- obj.language: de
- obj.specobject-type: heading
- ChapterName: 5.1.5 Besondere Maßnahmen bei Lithium-Ionen-Akkumulatoren

##### R157: Allgemeines (heading)
- bib.al.original-language: de
- bib.dp.publication-date: 2018-07-01
- ids.document: 7104561
- obj.clause-number: 5.1.5.1
- obj.element-name: heading
- obj.language: de
- obj.specobject-type: heading
- ChapterName: 5.1.5.1 Allgemeines

###### prov-7104561-5524de148c8c438: Allgemeines (provision)
Lithium-Ionen-Akkumulatoren sind vor allem anzutreffen:
- bei elektromobilen Anwendungen (z. B. Elektro- und Hybrid-Fahrzeugen, Pedelecs);
- in stationären Speichern (z. B. Haushaltsspeichern in Verbindung mit PV-Anlagen, Quartierspeichern und Großspeichern der Netzbetreiber);
- in Lagerstätten (z. B. Produktion, Handel, Entsorgung).
- bib.al.original-language: de
- bib.dp.publication-date: 2018-07-01
- ids.document: 7104561
- ids.tracing: hash-D7EEF4E70B1D3AD4E52397AD486ABC09685DC2A2339E1DECF8786B07025D59A5
- obj.clause-number: 5.1.5.1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### R159: Gefährdungen (heading)
- bib.al.original-language: de
- bib.dp.publication-date: 2018-07-01
- ids.document: 7104561
- obj.clause-number: 5.1.5.2
- obj.element-name: heading
- obj.language: de
- obj.specobject-type: heading
- ChapterName: 5.1.5.2 Gefährdungen

###### prov-7104561-d98db5b46d6947c: Gefährdungen (provision)
Folgende Gefährdungen können von Lithium-Ionen-Akkumulatoren ausgehen:
- elektrische (z. B. Rückspannung in die Elektroinstallation trotz Trennung vom örtlichen Stromversorgungsnetz);
- thermische (z. B. extreme Brandausbreitung);
- chemische (z. B. Flusssäure, giftige und brennbare Gase).
- bib.al.original-language: de
- bib.dp.publication-date: 2018-07-01
- ids.document: 7104561
- ids.tracing: hash-530685E6BD959B143D96C1DAF16AF283A00792373A4D3BB96BF4156D6DEDBDF6
- obj.clause-number: 5.1.5.2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-4385d643bf2d4cb: Gefährdungen (provision)
Diese vorstehend genannten Gefährdungen können auch zeitverzögert bis zu mehrere Stunden nach einer Schadenseinwirkung auftreten.
- bib.al.original-language: de
- bib.dp.publication-date: 2018-07-01
- ids.document: 7104561
- ids.tracing: hash-29BB875389A83E4EA296462A974B2DE995E25C321673614939626C4AC7E9C8FD
- obj.clause-number: 5.1.5.2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-0c7e224f62ee466: Gefährdungen (provision)
Auslöser eines Schadensereignisses können z. B. sein: Blitzeinschlag, Überspannung, Überschwemmung, Brand, mechanische Einwirkung.
- bib.al.original-language: de
- bib.dp.publication-date: 2018-07-01
- ids.document: 7104561
- ids.tracing: hash-A3433D1224CB8505EC55041123E0DBB3A595DBEA6A057A18F85F711139BF61FF
- obj.clause-number: 5.1.5.2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### R163: Maßnahmen (heading)
- bib.al.original-language: de
- bib.dp.publication-date: 2018-07-01
- ids.document: 7104561
- obj.clause-number: 5.1.5.3
- obj.element-name: heading
- obj.language: de
- obj.specobject-type: heading
- ChapterName: 5.1.5.3 Maßnahmen

###### prov-7104561-8f9b7caa64354b3: Maßnahmen (provision)
Nur die benötigten Einsatzkräfte dürfen den unmittelbaren Gefahrenbereich (in der Regel den betroffenen Raum) betreten.
- bib.al.original-language: de
- bib.dp.publication-date: 2018-07-01
- ids.document: 7104561
- ids.tracing: hash-4B1C2DC8071F5890BD1C9CF05A8458C3549F3D880B0F4A01D1E27424A4C470EB
- obj.clause-number: 5.1.5.3
- obj.element-name: paragraph
- obj.language: de
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-7daaa35970c44a0: Maßnahmen (provision)
Dabei sollten diese Einsatzkräfte den größtmöglichen Abstand halten bzw. aufgrund der extremen Brandausbreitung aus der Deckung arbeiten.
- bib.al.original-language: de
- bib.dp.publication-date: 2018-07-01
- ids.document: 7104561
- ids.tracing: hash-9CEA98B40667FB48AAE9DE5B12B72821E9A141C0667820634AE12C0BE008C982
- obj.clause-number: 5.1.5.3
- obj.element-name: paragraph
- obj.language: de
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-81d4cf672ffe447: Maßnahmen (provision)
Bei Verdacht auf beschädigte Lithium-Ionen-Akkumulatoren ist der Anlagenbetreiber über das Risiko der verzögerten Reaktion und des weiteren Betriebes zu informieren, damit er die sofortige Stilllegung und einen zeitnahen Ausbau des Lithium-Ionen-Akkumulators veranlassen kann.
- bib.al.original-language: de
- bib.dp.publication-date: 2018-07-01
- ids.document: 7104561
- ids.tracing: hash-498E2FE7783CC2D88DE14AAFE1B60E7DDE3AF20B54B2522DB2D009A2934D8536
- obj.clause-number: 5.1.5.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-724f6ee9f8cf494: Maßnahmen (provision)
Beim Einsatz können Personen und Geräte in Kontakt kommen mit:
- Elektrolyt oder
- Zersetzungsprodukten (u. a. Flusssäure in kontaminiertem Löschmittel).
- bib.al.original-language: de
- bib.dp.publication-date: 2018-07-01
- ids.document: 7104561
- ids.tracing: hash-82D1C5E40B8D0B403BA5595CED48272A2635F7A3BE55C9D1CAAE7B82AD3F1C16
- obj.clause-number: 5.1.5.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-9fd9bac87ab54e6: Maßnahmen (provision)
Für diesen Fall sind Maßnahmen nach der Feuerwehrdienstvorschrift 500 „Einheiten im ABC-Einsatz“ zu ergreifen.
- bib.al.original-language: de
- bib.dp.publication-date: 2018-07-01
- ids.document: 7104561
- ids.tracing: hash-DBC000E450591266DDD94A089713BBCF20A3E552B796251753EFA7405198F9B6
- obj.clause-number: 5.1.5.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-70beb7d4960f4ca: Maßnahmen (provision)
1. Brennende Lithium-Ionen-Akkumulatoren.
- bib.al.original-language: de
- bib.dp.publication-date: 2018-07-01
- ids.document: 7104561
- ids.tracing: hash-18696E64A6D62CF4ED3E7D54C7827F4326CE735B97DF8C36BB0AB154AA1FE03F
- obj.clause-number: 5.1.5.3
- obj.element-name: ordered-list
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-17fc18d230c24fb: Maßnahmen, list extract (provision)
- Brennende Lithium-Ionen-Akkumulatoren.
- bib.al.original-language: de
- bib.dp.publication-date: 2018-07-01
- ids.document: 7104561
- ids.tracing: hash-44BE7E0097E6DCBEC9D583D99EB6031253335AA1287C2E2257788561F1AB9BED
- obj.clause-number: 5.1.5.3
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-91633f2b70da401: Maßnahmen (provision)
Wasser ist aufgrund der Kühlwirkung als Löschmittel zu empfehlen.
- bib.al.original-language: de
- bib.dp.publication-date: 2018-07-01
- ids.document: 7104561
- ids.tracing: hash-AC5900FD2FB13650351BB81989D402ED9D9C803190772CCF37061F76699E1857
- obj.clause-number: 5.1.5.3
- obj.element-name: paragraph
- obj.language: de
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-ac159fc1c69e467: Maßnahmen (provision)
Brennende Lithium-Ionen-Akkumulatoren sind nur schwer zu löschen.
- bib.al.original-language: de
- bib.dp.publication-date: 2018-07-01
- ids.document: 7104561
- ids.tracing: hash-2D36C4A53D3007E35EC638E16F1E4DD0AC23902869A3C96A7151A97D7EB29D04
- obj.clause-number: 5.1.5.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-2e53137b713349d: Maßnahmen (provision)
Daher liegt das taktische Ziel der Einsatzmaßnahme auf der Verhinderung einer weiteren Brandausbreitung.
- bib.al.original-language: de
- bib.dp.publication-date: 2018-07-01
- ids.document: 7104561
- ids.tracing: hash-DC3169DEBC8A84E7D6F04755EDFF2C25E2841D1430D5864E59C146B77B477B4B
- obj.clause-number: 5.1.5.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-636a46dcac3343f: Maßnahmen (provision)
Bei Lagerstätten mit Lithium-Ionen-Akkumulatoren sind ggf. Maßnahmen zur Löschwasserrückhaltung erforderlich.
- bib.al.original-language: de
- bib.dp.publication-date: 2018-07-01
- ids.document: 7104561
- ids.tracing: hash-567972F6E18DB8719C5251EA9947C2412DF880717EE071B2B56AAA3C918E1CD5
- obj.clause-number: 5.1.5.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-ebfea2dcc8874e4: Maßnahmen (provision)
- 2) Vermeiden des Entzündens der Lithium-Ionen-Akkumulatoren.
- bib.al.original-language: de
- bib.dp.publication-date: 2018-07-01
- ids.document: 7104561
- ids.tracing: hash-A37363361244A65732C2D1C9A31CABF69036966FE5772124276B83BAEF684CFE
- obj.clause-number: 5.1.5.3
- obj.element-name: ordered-list
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-6c9dd36be024469: Maßnahmen, list extract (provision)
- Vermeiden des Entzündens der Lithium-Ionen-Akkumulatoren.
- bib.al.original-language: de
- bib.dp.publication-date: 2018-07-01
- ids.document: 7104561
- ids.tracing: hash-BF2813FB6224536448D3D66B03DEDB746C45D993AC910D54B910C05FC6B7C3BC
- obj.clause-number: 5.1.5.3
- obj.element-name: document
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-7f588ee077fb47c: Maßnahmen (provision)
Bei oder nach thermischer Einwirkung von außen (Akkumulatortemperatur ab etwa 80 °C) sollte der Lithium-Ionen-Akkumulator gekühlt werden, um sein Entzünden und/oder eine Gasfreisetzung zu verhindern (z. B. bei einem Zimmerbrand).
- bib.al.original-language: de
- bib.dp.publication-date: 2018-07-01
- ids.document: 7104561
- ids.tracing: hash-8A08BC4F67011694FFA66ADF46AF1A4D92BA796A3178B1F93C27EB311FC283AF
- obj.clause-number: 5.1.5.3
- obj.element-name: paragraph
- obj.language: de
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

#### R178: 5.1.6 (heading)
- bib.al.original-language: de
- bib.dp.publication-date: 2018-07-01
- ids.document: 7104561
- obj.element-name: heading
- obj.language: de
- obj.specobject-type: heading

##### prov-7104561-ff511d1898514ed (provision)
Beim Einsatz von Leitern, Teleskopmasten und anderen Geräten dürfen die unter 5.2.4, 5.3.4 und 5.3.5 angegebenen und jeweils zutreffenden Mindestabstände nicht unterschritten werden.
- bib.al.original-language: de
- bib.dp.publication-date: 2018-07-01
- ids.document: 7104561
- ids.tracing: hash-1482D5D37E0A2ED9C9D9A2C60F65D631408E3A178DEC20DA1894DBF7E1876C3C
- obj.clause-number: 5.1.6
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R198
- cross-reference -> R212
- cross-reference -> R219

##### prov-7104561-8f9e2aa5f92f408 (provision)
Hierbei ist die Annäherung durch Belastungen und Schwankungen zu berücksichtigen.
- bib.al.original-language: de
- bib.dp.publication-date: 2018-07-01
- ids.document: 7104561
- ids.tracing: hash-8A106F5FE0204995FCE0DB0AB125768F5C1C39B339C2D840059229E028DA816B
- obj.clause-number: 5.1.6
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### R181: 5.1.7 (heading)
- bib.al.original-language: de
- bib.dp.publication-date: 2018-07-01
- ids.document: 7104561
- obj.element-name: heading
- obj.language: de
- obj.specobject-type: heading

##### prov-7104561-6574a6c20caa438 (provision)
Nicht vom Brand betroffene elektrische Maschinen, Schalttafeln, Geräte, Fernmeldeanlagen usw. sind nach Möglichkeit vor Löschmitteln zu schützen.
- bib.al.original-language: de
- bib.dp.publication-date: 2018-07-01
- ids.document: 7104561
- ids.tracing: hash-E7958AB19ACF8127648E1C1FD9BC04F8FFF7C085AF56CB6D8C50CF03F06478F0
- obj.clause-number: 5.1.7
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### R183: 5.1.8 (heading)
- bib.al.original-language: de
- bib.dp.publication-date: 2018-07-01
- ids.document: 7104561
- obj.element-name: heading
- obj.language: de
- obj.specobject-type: heading

##### prov-7104561-84339b80bcd641b (provision)
Klimaanlagen, Lüftungsanlagen usw. sind so zu steuern, dass eine Ausbreitung von Brandrauch im Gebäude vermieden wird.
- bib.al.original-language: de
- bib.dp.publication-date: 2018-07-01
- ids.document: 7104561
- ids.tracing: hash-662BB7ED70AF0BECF5AF9CAE3DFEB88AD9B036BBD4A1CD3B4E65F49246A2839F
- obj.clause-number: 5.1.8
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### R185: Besondere Maßnahmen für Niederspannungsanlagen (heading)
- bib.al.original-language: de
- bib.dp.publication-date: 2018-07-01
- ids.document: 7104561
- obj.clause-number: 5.2
- obj.element-name: heading
- obj.language: de
- obj.specobject-type: heading
- ChapterName: 5.2 Besondere Maßnahmen für Niederspannungsanlagen

#### R186: 5.2.1 (heading)
- bib.al.original-language: de
- bib.dp.publication-date: 2018-07-01
- ids.document: 7104561
- obj.element-name: heading
- obj.language: de
- obj.specobject-type: heading

##### prov-7104561-5c201a589f5748a (provision)
Sind im Bereich der Einsatzstelle umfangreiche Zerstörungen der Niederspannungsanlagen, insbesondere der Freileitungen, zu erwarten oder bereits eingetreten, so sind die betroffenen Leitungen im Bereich der Einsatzstelle spannungsfrei zu machen [siehe DIN VDE 0105-100 (VDE 0105-100):2015-10, 6.2] .
- bib.al.original-language: de
- bib.dp.publication-date: 2018-07-01
- ids.document: 7104561
- ids.tracing: hash-C1E732FCD854610A3101AEC4B86AE1C2B0FC14D7CD1064C2CBF87D097236394D
- obj.clause-number: 5.2.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-1c816b4c335f450: , Note (provision)
ANMERKUNG:
Diese Maßnahme ist erforderlich, weil der Isolationszustand, z. B. durch Brandeinwirkung oder Löschmaßnahmen unter Umständen erheblich herabgesetzt werden kann, und weil Freileitungen reißen können.
- bib.al.original-language: de
- bib.dp.publication-date: 2018-07-01
- ids.document: 7104561
- ids.tracing: hash-1F69200653608A4D59CBACA0392398E37B8AE3E8B5B6740EF1F89E9CD606593C
- obj.clause-number: 5.2.1
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-7104561-c824d75017de458 (provision)
Eine Berührung von herabgefallenen Leitungen, auch wenn sie am Boden liegen, und eine Berührung der im normalen Zustand nicht unter Spannung stehenden Metallteile, z. B. Maschinen, Fernmelde-Freileitungen, Antennen, Blechdächer und -wände, Regenrinnen, Wasser- oder Gasleitungen, Metallzäune, kann gefährlich sein.
- bib.al.original-language: de
- bib.dp.publication-date: 2018-07-01
- ids.document: 7104561
- ids.tracing: hash-C4806101DD164E3DA624C1629B68593F007766C6081B70885CFD54D2EEAD9658
- obj.clause-number: 5.2.1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-894bed1895c647d (provision)
Diese Metallteile können unter Umständen unter Spannung stehen.
- bib.al.original-language: de
- bib.dp.publication-date: 2018-07-01
- ids.document: 7104561
- ids.tracing: hash-0B0F9E99AC964F6AFD0837F63F474CE24302893049464AC2E785A85DDA917F1E
- obj.clause-number: 5.2.1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### R191: 5.2.2 (heading)
- bib.al.original-language: de
- bib.dp.publication-date: 2018-07-01
- ids.document: 7104561
- obj.element-name: heading
- obj.language: de
- obj.specobject-type: heading

##### prov-7104561-90cd01bba7be467 (provision)
Schalthandlungen in Niederspannungsanlagen dürfen nur von Elektrofachkräften oder elektrotechnisch unterwiesenen Personen vorgenommen werden.
- bib.al.original-language: de
- bib.dp.publication-date: 2018-07-01
- ids.document: 7104561
- ids.tracing: hash-4E75EBA3E934E8214E231C487DF164DB5F442C06311667E35573608E981CE43B
- obj.clause-number: 5.2.2
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-9a531e5de7c0481 (provision)
Hiervon ausgenommen sind Hausinstallationen.
- bib.al.original-language: de
- bib.dp.publication-date: 2018-07-01
- ids.document: 7104561
- ids.tracing: hash-B1317C7141546099D1F3BFB49504D54150768F2B86FDB0A18EA4A07B374AB4E4
- obj.clause-number: 5.2.2
- obj.element-name: paragraph
- obj.language: de
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-c429b9b17d444f9: , Note (provision)
ANMERKUNG:
Zur Hausinstallation im Sinne dieser Norm gehören auch elektromedizinische Geräte, Leuchtröhrenanlagen, z. B. für Reklame, die zwar mit Hochspannung betrieben werden, jedoch an die Hausinstallation angeschlossen sind und dort geschaltet werden können.
- bib.al.original-language: de
- bib.dp.publication-date: 2018-07-01
- ids.document: 7104561
- ids.tracing: hash-24C3711CD1212F9E9A3B85A67EF90F255B22EE0CE5C35F55175C51509F33BB56
- obj.clause-number: 5.2.2
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### R195: 5.2.3 (heading)
- bib.al.original-language: de
- bib.dp.publication-date: 2018-07-01
- ids.document: 7104561
- obj.element-name: heading
- obj.language: de
- obj.specobject-type: heading

##### prov-7104561-0de8151afb0e4c2 (provision)
Unsachgemäßes Kurzschließen oder Durchtrennen von unter Spannung stehenden Leitungen und Kabeln ist lebensgefährlich.
- bib.al.original-language: de
- bib.dp.publication-date: 2018-07-01
- ids.document: 7104561
- ids.tracing: hash-C94E04CE53791E9ECA9820F9A6B966FBC2771D6B2DDE2383AAA70DC654845DD0
- obj.clause-number: 5.2.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-e69a2f1d2bc0426 (provision)
Kurzschließen oder Durchtrennen von unter Spannung stehenden Leitungen und Kabeln als Notmaßnahme darf daher nur bei Gefährdung von Menschenleben und nur von Elektrofachkräften durchgeführt werden.
- bib.al.original-language: de
- bib.dp.publication-date: 2018-07-01
- ids.document: 7104561
- ids.tracing: hash-66A45AD679A30B77EF02B816C9993BDBD7B166B1F8F131126044219E65090517
- obj.clause-number: 5.2.3
- obj.element-name: paragraph
- obj.language: de
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

#### R198: 5.2.4 (heading)
- bib.al.original-language: de
- bib.dp.publication-date: 2018-07-01
- ids.document: 7104561
- obj.element-name: heading
- obj.language: de
- obj.specobject-type: heading

##### prov-7104561-41daf97bd94d465 (provision)
Bei Annäherung (z. B. beim Erkunden und Retten) an unter Spannung stehende Niederspannungsanlagenteile ist der Mindestabstand nach Tabelle 2 einzuhalten.
- bib.al.original-language: de
- bib.dp.publication-date: 2018-07-01
- ids.document: 7104561
- ids.tracing: hash-87294E012B6A87CE4FEC035DC502FDD786D8CD466E751509FA1B3307F226F520
- obj.clause-number: 5.2.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-b2af74b355cb46d

##### prov-7104561-f47e76e9ef0b4fb (provision)
Dieser Abstand ist nicht erforderlich, wenn diese elektrischen Anlagenteile in frei zugänglichen Räumen offensichtlich unbeschädigt sind (z. B. Abstand zu Lichtschaltern und Steckdosen).
- bib.al.original-language: de
- bib.dp.publication-date: 2018-07-01
- ids.document: 7104561
- ids.tracing: hash-167040298FEF963AFBFEC4EEAD13B2082D0C00FF6FD16678F610E360F0B26B8F
- obj.clause-number: 5.2.4
- obj.element-name: paragraph
- obj.language: de
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-b2af74b355cb46d: Zulässige Annäherungen in Niederspannungsanlagen (provision)
Tabelle 2 — Zulässige Annäherungen in Niederspannungsanlagen
| Nennspannung | Annäherung |
| --- | --- |
| bis AC 1 000 V oder DC 1 500 V | 1 m |
- bib.al.original-language: de
- bib.dp.publication-date: 2018-07-01
- ids.document: 7104561
- ids.tracing: hash-2C19F56A4172A1DBDB4299AE43A0F30AF17A9C84F94C80564FA8C96C012B033C
- obj.clause-number: Tabelle 2
- obj.element-name: table
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-3ac830c4ee9b486 (provision)
Bei Löscharbeiten gelten die Mindestabstände nach den Tabellen 5 bis 8.
- bib.al.original-language: de
- bib.dp.publication-date: 2018-07-01
- ids.document: 7104561
- ids.tracing: hash-51C632CD36B7349AB660BFBC8C02F0346FCE7814655366A85933593CAE13CB1C
- obj.clause-number: 5.2.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-69867da9b1324e0

### R203: Besondere Maßnahmen für Hochspannungsanlagen (heading)
- bib.al.original-language: de
- bib.dp.publication-date: 2018-07-01
- ids.document: 7104561
- obj.clause-number: 5.3
- obj.element-name: heading
- obj.language: de
- obj.specobject-type: heading
- ChapterName: 5.3 Besondere Maßnahmen für Hochspannungsanlagen

#### R204: 5.3.1 (heading)
- bib.al.original-language: de
- bib.dp.publication-date: 2018-07-01
- ids.document: 7104561
- obj.element-name: heading
- obj.language: de
- obj.specobject-type: heading

##### prov-7104561-754f9266525044e (provision)
Hochspannungsanlagen in abgeschlossenen elektrischen Betriebsstätten, wie z. B. Schalt- und Umspannanlagen, dürfen nur in Gegenwart einer für den Betrieb dieser Anlage verantwortlichen Person und nur von unmittelbar Beteiligten betreten werden.
- bib.al.original-language: de
- bib.dp.publication-date: 2018-07-01
- ids.document: 7104561
- ids.tracing: hash-66928D56B4BAE718F7A4894790AF3C5FEB6028294588678F40063F2D8AAE5B7D
- obj.clause-number: 5.3.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-b1771104d94a494 (provision)
Zur Rettung von Menschenleben ist das Betreten auch bei Abwesenheit dieser Person möglich, wenn eine Elektrofachkraft anwesend ist, die über spezielle Kenntnisse für Hochspannungsanlagen der entsprechenden Spannungsebene verfügt.
- bib.al.original-language: de
- bib.dp.publication-date: 2018-07-01
- ids.document: 7104561
- ids.tracing: hash-B495367EDA688EBC79C7770CFAE64F3EBD7A3CBB8CCE7EF82C03B70D70B7F1B7
- obj.clause-number: 5.3.1
- obj.element-name: paragraph
- obj.language: de
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-2a80a00a38c243b (provision)
Für im unmittelbaren Einflussbereich eines Brandes liegende Anlagenteile ist – wegen der Gefahr von Lichtbogenkurzschlüssen durch leitfähige Beläge, Ionisation usw. – vor Annäherung der spannungsfreie Zustand herzustellen und sicherzustellen [siehe DIN VDE 0105-100 (VDE 0105-100):2015-10, 6.2] .
- bib.al.original-language: de
- bib.dp.publication-date: 2018-07-01
- ids.document: 7104561
- ids.tracing: hash-112CE3A0A0B5CDCC871D36AE73CA11D5BE633D92864F8EB6CCADE26BED56EE64
- obj.clause-number: 5.3.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### R208: 5.3.2 (heading)
- bib.al.original-language: de
- bib.dp.publication-date: 2018-07-01
- ids.document: 7104561
- obj.element-name: heading
- obj.language: de
- obj.specobject-type: heading

##### prov-7104561-3e481efa9f75464 (provision)
Schalthandlungen in Hochspannungsanlagen dürfen nur durch den Anlagenverantwortlichen veranlasst werden.
- bib.al.original-language: de
- bib.dp.publication-date: 2018-07-01
- ids.document: 7104561
- ids.tracing: hash-BF96F71AAD8D072F3EB04B861431E637A51A024085A1C32630EBABE4A2E837E6
- obj.clause-number: 5.3.2
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### R210: 5.3.3 (heading)
- bib.al.original-language: de
- bib.dp.publication-date: 2018-07-01
- ids.document: 7104561
- obj.element-name: heading
- obj.language: de
- obj.specobject-type: heading

##### prov-7104561-8e1c16828b15484 (provision)
Hochspannungsanlagen, z. B. Freileitungen, dürfen unter keinen Umständen durch behelfsmäßiges Erden und Kurzschließen oder Durchtrennen spannungsfrei gemacht werden, weil diese Maßnahmen mit nicht überschaubaren Gefahren verbunden sind.
- bib.al.original-language: de
- bib.dp.publication-date: 2018-07-01
- ids.document: 7104561
- ids.tracing: hash-B91826058B2795D6BE0FFF9A9A6A2BBD56F0FEAFC61D226DA701096D337759C7
- obj.clause-number: 5.3.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### R212: 5.3.4 (heading)
- bib.al.original-language: de
- bib.dp.publication-date: 2018-07-01
- ids.document: 7104561
- obj.element-name: heading
- obj.language: de
- obj.specobject-type: heading

##### prov-7104561-0595dc94cff1442 (provision)
Bei Annäherung (z. B. beim Erkunden und Retten) an unter Spannung stehende Hochspannungsanlagen in nicht abgeschlossenen elektrischen Betriebsstätten, z. B. Freileitungen, sind die Mindestabstände nach Tabelle 3 einzuhalten.
- bib.al.original-language: de
- bib.dp.publication-date: 2018-07-01
- ids.document: 7104561
- ids.tracing: hash-8F2C12CE33C5F8128D60A50934930C860DFB2A784261EC8B4FF11BF6F69D4FB7
- obj.clause-number: 5.3.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-2a77f3e81b6942f

##### prov-7104561-c6b35576eb74409 (provision)
Bei Unterschreiten dieser Mindestabstände besteht Lebensgefahr.
- bib.al.original-language: de
- bib.dp.publication-date: 2018-07-01
- ids.document: 7104561
- ids.tracing: hash-06EBC83DCB4EA3CF938700A27C5D9BBE05CFDBE6EEFBAA09C62612DFFDC46F8D
- obj.clause-number: 5.3.4
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-2a77f3e81b6942f: Zulässige Annäherungen in Hochspannungsanlagen (provision)
Tabelle 3 — Zulässige Annäherungen in Hochspannungsanlagen
| Nennspannung | Annäherung |
| --- | --- |
| bis 110 kV | 3 m |
| über 110 kV bis 220 kV | 4 m |
| über 220 kV bis 380 kV | 5 m |
- bib.al.original-language: de
- bib.dp.publication-date: 2018-07-01
- ids.document: 7104561
- ids.tracing: hash-5B1B0B811308772C4CED7ECF214C517DA08E06E7F5910D58D1E3C689F7C78E9B
- obj.clause-number: Tabelle 3
- obj.element-name: table
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-f4f5e124eecb4bb (provision)
Unter Aufsicht von Elektrofachkräften oder elektrotechnisch unterwiesenen Personen ist eine Annäherung bis auf die Werte nach DIN VDE 0105-100 (VDE 0105-100):2015-10, Tabelle 102 möglich.
- bib.al.original-language: de
- bib.dp.publication-date: 2018-07-01
- ids.document: 7104561
- ids.tracing: hash-2E8632B85B08D49648EDB6A0B271DDB55360657C7A1E9AE249959A54984267A3
- obj.clause-number: 5.3.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-1cbf7aae04584c6 (provision)
Bei Rettungsarbeiten an Oberleitungen elektrischer Bahnen (bis 25 kV) ist eine Annäherung bis auf 1,5 m möglich [siehe DIN VDE 0105-103 (VDE 0105-103):2014-10, 6.4 .302].
- bib.al.original-language: de
- bib.dp.publication-date: 2018-07-01
- ids.document: 7104561
- ids.tracing: hash-8A8642ECA64211C75667308C00731293072C75982A11A3A297BCAF2C910F5841
- obj.clause-number: 5.3.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-f8d842379df6417 (provision)
Bei Löscharbeiten gelten die Mindestabstände nach den Tabellen 5 bis 8.
- bib.al.original-language: de
- bib.dp.publication-date: 2018-07-01
- ids.document: 7104561
- ids.tracing: hash-BE9734A758CF10B62E90255A00B09E3BD3B26DF2321054F97B143981FC24F085
- obj.clause-number: 5.3.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-69867da9b1324e0

#### R219: 5.3.5 (heading)
- bib.al.original-language: de
- bib.dp.publication-date: 2018-07-01
- ids.document: 7104561
- obj.element-name: heading
- obj.language: de
- obj.specobject-type: heading

##### prov-7104561-9a4a1902d73c4e2 (provision)
Freileitungen und Fahrleitungen in der Nähe von Einsatzstellen können beschädigt werden und herunterfallen.
- bib.al.original-language: de
- bib.dp.publication-date: 2018-07-01
- ids.document: 7104561
- ids.tracing: hash-3796B5DC122A3C3AB8A251A17EB12D78F056F35C1B830E95C0683F5BEB179DE9
- obj.clause-number: 5.3.5
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-03a5de5fffec485 (provision)
Das Betreten der Umgebung von herabgefallenen, unter Spannung stehenden Leitungen ist lebensgefährlich (Schrittspannung, siehe Bild 1).
- bib.al.original-language: de
- bib.dp.publication-date: 2018-07-01
- ids.document: 7104561
- ids.tracing: hash-0FFABB23FD38C938F1D60DA5A74B159D1026C1CD6DE27F9A8504E565C870DDAA
- obj.clause-number: 5.3.5
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-9acf97ebc2404d7

##### prov-7104561-9acf97ebc2404d7 (provision)
Bild 1 — SchrittspannungU _S im Bereich einer Fehlerstelle bei der Schrittlänge l _S
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| Legende |  |
| --- | --- |
| U _S1 | Schrittspannung 1 |
| U _S2 | Schrittspannung 2 |
| l _S | Schrittlänge |
| Legende |  |
| --- | --- |
| U _S1 | Schrittspannung 1 |
| U _S2 | Schrittspannung 2 |
| l _S | Schrittlänge |
- bib.al.original-language: de
- bib.dp.publication-date: 2018-07-01
- ids.document: 7104561
- ids.tracing: hash-C1273516E1ADB10EF17533052DA7016A8591CA27C0C165989CB8460D701C14FC
- obj.clause-number: 5.3.5
- obj.element-name: figure
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-708da280f279472 (provision)
Von der am Boden liegenden Freileitung ist daher ein Abstand von mindestens 20 m, von der am Boden liegenden Fahrleitung ein Abstand von 10 m einzuhalten.
- bib.al.original-language: de
- bib.dp.publication-date: 2018-07-01
- ids.document: 7104561
- ids.tracing: hash-4582C599B9F607A2B7C014D0A4C0D8D80072BF16BAC4888E8895D01C94D192A8
- obj.clause-number: 5.3.5
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-c6ba2ecdae034b0 (provision)
Hat die betreffende Leitung Berührung mit Metallteilen wie Zäunen, Geländern, Schienen usw., so ist von diesen Teilen ebenfalls der entsprechende Abstand einzuhalten.
- bib.al.original-language: de
- bib.dp.publication-date: 2018-07-01
- ids.document: 7104561
- ids.tracing: hash-9E1D8AFC83374E6D7668475A68FA14201379FB118A98CF72CF7811899A79ACBB
- obj.clause-number: 5.3.5
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-9ae25e6bf1ac416 (provision)
Die Gefahrenzone ist abzusperren.
- bib.al.original-language: de
- bib.dp.publication-date: 2018-07-01
- ids.document: 7104561
- ids.tracing: hash-4455EB7C209330C7D00C57DB5CFB0F5FD17F4C2CB0AB042215B41884DBF71E0E
- obj.clause-number: 5.3.5
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-ee26db0017484d4 (provision)
Der Bereich darf erst wieder nach Beseitigung der Gefahr und Freigabe durch den Anlagenbetreiber betreten werden.
- bib.al.original-language: de
- bib.dp.publication-date: 2018-07-01
- ids.document: 7104561
- ids.tracing: hash-58923A70B6962C233AD4C1C88912C20D116B054DFDB9FD7CC73582AE70E5C657
- obj.clause-number: 5.3.5
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-0cb6fa6d738e484: , Note (provision)
ANMERKUNG:
Mit den vorstehenden Abständen soll sichergestellt werden, dass selbst bei ungünstigen Bedingungen keine Gefährdung für die Einsatzkräfte vorliegt. Ungünstige Bedingungen liegen z. B. bei gelöschten 110-kV-Netzen und gleichzeitig hohen spezifischen Erdwiderständen vor.
- bib.al.original-language: de
- bib.dp.publication-date: 2018-07-01
- ids.document: 7104561
- ids.tracing: hash-135C8B0918A473B4702C0778489FBF45ED5018DFE136476E763B3B735CEA9F63
- obj.clause-number: 5.3.5
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### prov-7104561-78586fe23550422 (provision)
Jedoch kann eine Elektrofachkraft des betreffenden Anlagenbetreibers des Elektrizitätsversorgungsnetzes, die beurteilen kann, um welche Netzspannungsebene und Art der Sternpunkterdung es sich handelt, vor Ort den Einsatzkräften empfehlen, auf welchen Wert der Schutzabstand gegebenenfalls unter 20 m verringert werden kann.
- bib.al.original-language: de
- bib.dp.publication-date: 2018-07-01
- ids.document: 7104561
- ids.tracing: hash-B3D14F6599DB0D2911392A1FFE603178CF3D4951314B1C858A91E618039D496B
- obj.clause-number: 5.3.5
- obj.element-name: paragraph
- obj.language: de
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

##### prov-7104561-95f926f89e31425 (provision)
Dabei kann in Betracht gezogen werden, dass z. B.:
- in Niederspannungsnetzen keine gefahrbringenden Schrittspannungen vorkommen;
- im Hochspannungsbereich bis 30 kV (Mittelspannungsbereich) der Schutzabstand auf bis zu 10 m reduziert werden kann;
- bei den Spannungsebenen 220 kV und 380 kV die Sternpunkte grundsätzlich niederohmig geerdet sind und ein Erdschluss daher in kurzer Zeit abgeschaltet wird; das Gleiche gilt auch für niederohmig geerdete 110-kV-Netze;
- in gelöschten 110-kV-Netzen und gleichzeitig hohen spezifischen Erdwiderständen eine Reduzierung des Schutzabstandes unter 20 m nicht empfohlen wird.
- bib.al.original-language: de
- bib.dp.publication-date: 2018-07-01
- ids.document: 7104561
- ids.tracing: hash-387014AE79D08DE39F4ECB7AC52DA51DAAD85B2CBCA09C3D26A9B6E22A587578
- obj.clause-number: 5.3.5
- obj.element-name: paragraph
- obj.language: de
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

##### prov-7104561-3a13f1a956394ff (provision)
Den Angaben für den Schutzabstand liegen die Annahmen eines spezifischen Erdwiderstandes von 1 000 Ωm, eines Erdschlussreststromes von 132 A sowie einer maximalen Schrittspannung von 75 V zugrunde.
- bib.al.original-language: de
- bib.dp.publication-date: 2018-07-01
- ids.document: 7104561
- ids.tracing: hash-D274279B02C3C9EC103C9388E9843750FFB8F0EF108206B063CA27CD2BE77365
- obj.clause-number: 5.3.5
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### R231: Besondere Maßnahmen für Anlagen mit starken Magnetfeldern – supraleitende Magnete (heading)
- bib.al.original-language: de
- bib.dp.publication-date: 2018-07-01
- ids.document: 7104561
- obj.clause-number: 5.4
- obj.element-name: heading
- obj.language: de
- obj.specobject-type: heading
- ChapterName: 5.4 Besondere Maßnahmen für Anlagen mit starken Magnetfeldern – supraleitende Magnete

#### R232: Magnetische Supraleiter und deren Anwendungen (heading)
- bib.al.original-language: de
- bib.dp.publication-date: 2018-07-01
- ids.document: 7104561
- obj.clause-number: 5.4.1
- obj.element-name: heading
- obj.language: de
- obj.specobject-type: heading
- ChapterName: 5.4.1 Magnetische Supraleiter und deren Anwendungen

##### R233: Allgemeines (heading)
- bib.al.original-language: de
- bib.dp.publication-date: 2018-07-01
- ids.document: 7104561
- obj.clause-number: 5.4.1.1
- obj.element-name: heading
- obj.language: de
- obj.specobject-type: heading
- ChapterName: 5.4.1.1 Allgemeines

###### prov-7104561-a1d48fa4c8f040d: Allgemeines (provision)
Supraleitende Magnete werden
- in Forschungseinrichtungen (bis zu 20 Tesla) und
- vor allem im medizinischen Bereich der Kernspintomographen bzw. Magnetresonanztomographen (MRT) mit 0,5 Tesla bis 7 Tesla
verwendet.
- bib.al.original-language: de
- bib.dp.publication-date: 2018-07-01
- ids.document: 7104561
- ids.tracing: hash-4117DAC06AABFF7848EE5D5BFA355C59B706479DFAAAEDD016B6FD33099E1BF4
- obj.clause-number: 5.4.1.1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-53237e958b42452: Allgemeines, Note (provision)
ANMERKUNG 1:
Supraleitende Magnete werden auch als elektrische Energiespeicher und als Kurzschlussstrombegrenzer in Hochspannungsnetzen eingesetzt (z. B. Hochspannungsgleichstromübertragung – HGÜ).
- bib.al.original-language: de
- bib.dp.publication-date: 2018-07-01
- ids.document: 7104561
- ids.tracing: hash-2F93B68CD6915DDA6252117F2B5C95ADFDF7689FBA675B62C0098608D15F992D
- obj.clause-number: 5.4.1.1
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

###### prov-7104561-47894a9281bf4b1: Allgemeines, Note (provision)
ANMERKUNG 2:
Ein Tesla entspricht der 10 000-fachen Stärke des Erdmagnetfeldes.
- bib.al.original-language: de
- bib.dp.publication-date: 2018-07-01
- ids.document: 7104561
- ids.tracing: hash-C45C7BF6C0B9664FC17D2CD72C95F4FA304E8220FD254B1B8B294878B7368A50
- obj.clause-number: 5.4.1.1
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

##### R237: Gefährdungen (heading)
- bib.al.original-language: de
- bib.dp.publication-date: 2018-07-01
- ids.document: 7104561
- obj.clause-number: 5.4.1.2
- obj.element-name: heading
- obj.language: de
- obj.specobject-type: heading
- ChapterName: 5.4.1.2 Gefährdungen

###### prov-7104561-b7dcfd75ca4741a: Gefährdungen (provision)
Das Magnetfeld bei Supraleitern ist dauerhaft auch bei abgeschalteter Stromversorgung vorhanden.
- bib.al.original-language: de
- bib.dp.publication-date: 2018-07-01
- ids.document: 7104561
- ids.tracing: hash-BF1C63AF436A8B13E01FF5A9D0ACB3BFD51B4C3B06B9EB26556103B833267F2F
- obj.clause-number: 5.4.1.2
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-6114576bacec4a2: Gefährdungen (provision)
Sämtliche ferromagnetischen Teile können in das Magnetfeld gezogen werden.
- bib.al.original-language: de
- bib.dp.publication-date: 2018-07-01
- ids.document: 7104561
- ids.tracing: hash-3973A757DC2270ED43FD516687DDA8F8C965C0952F102D9A33D6A63CF73F0EAE
- obj.clause-number: 5.4.1.2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-b528acddeaa544e: Gefährdungen (provision)
Eine besondere Gefährdung besteht für Einsatzkräfte mit ferromagnetischen Atemschutzflaschen.
- bib.al.original-language: de
- bib.dp.publication-date: 2018-07-01
- ids.document: 7104561
- ids.tracing: hash-A038775BFA84D458AAE273F83290733E594C6A514FDF1870BCD5E4F49449872F
- obj.clause-number: 5.4.1.2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-e84db64e3e9342c: Gefährdungen (provision)
Der Atemschutzgeräteträger kann unvermittelt in oder an den supraleitenden Magneten gezogen werden.
- bib.al.original-language: de
- bib.dp.publication-date: 2018-07-01
- ids.document: 7104561
- ids.tracing: hash-7480A5221A3D40F9C98A91C478C5B3DD87EF694D74D0F4BE71C4BC242F938950
- obj.clause-number: 5.4.1.2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-e2dceb92d0b1446: Gefährdungen (provision)
Auch können Ausrüstungsgegenstände, Werkzeuge, Feuerlöscher, Krankenbetten oder Ähnliches in oder an supraleitende Magnete gezogen werden.
- bib.al.original-language: de
- bib.dp.publication-date: 2018-07-01
- ids.document: 7104561
- ids.tracing: hash-6DE93869E7AFEC107B7D15B6CEF327C15B018E9039B927C3EBF950293FCCF4DB
- obj.clause-number: 5.4.1.2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### R243: Maßnahmen (heading)
- bib.al.original-language: de
- bib.dp.publication-date: 2018-07-01
- ids.document: 7104561
- obj.clause-number: 5.4.1.3
- obj.element-name: heading
- obj.language: de
- obj.specobject-type: heading
- ChapterName: 5.4.1.3 Maßnahmen

###### prov-7104561-eb7c0c6b1c05455: Maßnahmen (provision)
Nur die benötigten Einsatzkräfte dürfen den unmittelbaren Gefahrenbereich (in der Regel den betroffenen Raum) betreten.
- bib.al.original-language: de
- bib.dp.publication-date: 2018-07-01
- ids.document: 7104561
- ids.tracing: hash-1930B56FA790726B4A41D69103DE29BAF296A5E40C974B4A4F008B4773452007
- obj.clause-number: 5.4.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-20045a17e3184e4: Maßnahmen (provision)
Dabei sollten diese Einsatzkräfte den größtmöglichen Abstand halten.
- bib.al.original-language: de
- bib.dp.publication-date: 2018-07-01
- ids.document: 7104561
- ids.tracing: hash-4C9A95DBF41E0821E7817BDD728AF969D2129A287860ACC9A515F1129096B9D9
- obj.clause-number: 5.4.1.3
- obj.element-name: paragraph
- obj.language: de
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-6553f56b82ba4b1: Maßnahmen (provision)
Das Betreten von Räumen mit starken Magnetfeldern ist nur mit nicht ferromagnetischen Ausrüstungsgegenständen, z. B. Komposit-Atemschutzflaschen, zulässig.
- bib.al.original-language: de
- bib.dp.publication-date: 2018-07-01
- ids.document: 7104561
- ids.tracing: hash-CE76CD30F2CD5106217F162473DB15BB43D810A4E7B7A1D846E43A98844E71A6
- obj.clause-number: 5.4.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-67aa9377d4c3419: Maßnahmen (provision)
Zum Löschen von Entstehungsbränden dürfen nur nicht ferromagnetische Feuerlöscher verwendet werden (Handelsbegriff: „antimagnetisch“).
- bib.al.original-language: de
- bib.dp.publication-date: 2018-07-01
- ids.document: 7104561
- ids.tracing: hash-AA2E8BE84DC5FD969A7FB357B1E772C384BFA517859D5D5AC0348C97354A81A8
- obj.clause-number: 5.4.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-df82a8517386454: Maßnahmen (provision)
Eine schnelle Abschaltung des Magnetfeldes ist nur in Form einer Notabschaltung über ein Ablassen des Kühlmittels (in der Regel flüssiges Helium bei 4 K) möglich.
- bib.al.original-language: de
- bib.dp.publication-date: 2018-07-01
- ids.document: 7104561
- ids.tracing: hash-8DCBEF06C7D6841133714C3FF4CBFD5EFEE12B38BFEACD56DC11726146F7D90B
- obj.clause-number: 5.4.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-861af8691edf4a3: Maßnahmen (provision)
Eine Notabschaltung des Magnetfeldes kann eine Gefährdung durch ausströmendes tiefkaltes Gas verursachen.
- bib.al.original-language: de
- bib.dp.publication-date: 2018-07-01
- ids.document: 7104561
- ids.tracing: hash-CCC56A64FB0EB172D86D0AFFE0D57123195D70C33434043A7844C363600C040E
- obj.clause-number: 5.4.1.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-59796b2736ca482: Maßnahmen (provision)
Die Notabschaltung der elektrischen Komponenten erfolgt über einen separaten Not-Aus-Schalter und hat keinen Einfluss auf das Magnetfeld.
- bib.al.original-language: de
- bib.dp.publication-date: 2018-07-01
- ids.document: 7104561
- ids.tracing: hash-F5C7E660A9E8E150352320E45770A5CCAE03CEB1115B36B91BD5316F265137FE
- obj.clause-number: 5.4.1.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-fb918fbdd865434: Maßnahmen (provision)
Abschaltungen sind, außer bei Lebensgefahr, zuvor mit dem Anlagenbetreiber abzusprechen.
- bib.al.original-language: de
- bib.dp.publication-date: 2018-07-01
- ids.document: 7104561
- ids.tracing: hash-282AA2BE804D74A4E6975566C2C30BABAED5F311514D8363EEC604BBFE73195D
- obj.clause-number: 5.4.1.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

###### prov-7104561-5b0209dbab934f1: Maßnahmen, Note (provision)
ANMERKUNG:
Eine Notabschaltung verursacht sehr hohe Kosten und kann zu einer Beschädigung oder Zerstörung des Magneten führen.
- bib.al.original-language: de
- bib.dp.publication-date: 2018-07-01
- ids.document: 7104561
- ids.tracing: hash-C2D0DB1BD19778E6F97FC79433E620920EE92B3C95651338A5515268249E0170
- obj.clause-number: 5.4.1.3
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

## R253: Eignung von Löschmitteln (heading)
- bib.al.original-language: de
- bib.dp.publication-date: 2018-07-01
- ids.document: 7104561
- obj.clause-number: 6
- obj.element-name: heading
- obj.language: de
- obj.specobject-type: heading
- ChapterName: 6 Eignung von Löschmitteln

### R254: Auswahl der Löschmittel (heading)
- bib.al.original-language: de
- bib.dp.publication-date: 2018-07-01
- ids.document: 7104561
- obj.clause-number: 6.1
- obj.element-name: heading
- obj.language: de
- obj.specobject-type: heading
- ChapterName: 6.1 Auswahl der Löschmittel

#### prov-7104561-a3b91eacea10444: Auswahl der Löschmittel (provision)
Als Löschmittel können z. B. eingesetzt werden:
- Wasser;
- Schaum;
- Pulver;
- Kohlenstoffdioxid.
- bib.al.original-language: de
- bib.dp.publication-date: 2018-07-01
- ids.document: 7104561
- ids.tracing: hash-CF7193F3A4FD467ADA6F89992B072CA565B1C8E94EDEAB714D2B95D592758B25
- obj.clause-number: 6.1
- obj.element-name: paragraph
- obj.language: de
- obj.modality: permission
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-2fb6abb45b2c4b4: Auswahl der Löschmittel (provision)
Diese Löschmittel sind unter Beachtung ihrer Eignung und eventueller Einsatzbeschränkungen auszuwählen.
- bib.al.original-language: de
- bib.dp.publication-date: 2018-07-01
- ids.document: 7104561
- ids.tracing: hash-63ADB1E429BD0BD7F740C226E327DACAAF26ABC46476CCFD6DE7BA548758EB59
- obj.clause-number: 6.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### R257: Anwendung von Löschmitteln (heading)
- bib.al.original-language: de
- bib.dp.publication-date: 2018-07-01
- ids.document: 7104561
- obj.clause-number: 6.2
- obj.element-name: heading
- obj.language: de
- obj.specobject-type: heading
- ChapterName: 6.2 Anwendung von Löschmitteln

#### R258: Allgemeines (heading)
- bib.al.original-language: de
- bib.dp.publication-date: 2018-07-01
- ids.document: 7104561
- obj.clause-number: 6.2.1
- obj.element-name: heading
- obj.language: de
- obj.specobject-type: heading
- ChapterName: 6.2.1 Allgemeines

##### prov-7104561-5153390ac5d34a6: Allgemeines (provision)
Die in den Tabellen 5 bis 8 genannten Mindestabstände zwischen Löschmittelaustrittsöffnung und unter Spannung stehenden Teilen der elektrischen Anlagen sind erforderlich, um Stromeinwirkungen auf das den Löscheinsatz durchführende Personal zu verhindern.
- bib.al.original-language: de
- bib.dp.publication-date: 2018-07-01
- ids.document: 7104561
- ids.tracing: hash-9BF59816F11F000AF509C8A025F2D82A997469E5947930855E989F49CD6865AD
- obj.clause-number: 6.2.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-69867da9b1324e0

##### prov-7104561-6a1f25d4f4a6445: Allgemeines (provision)
Dabei ist nicht nur die Gefährdung durch den elektrischen Strom, sondern auch die Gefährdung durch reflexartige Handlungen zu verhindern.
- bib.al.original-language: de
- bib.dp.publication-date: 2018-07-01
- ids.document: 7104561
- ids.tracing: hash-EFAEBA541DAE0FA3EE385EA46DAB857F3692468BFA09D0B04862056296AF3928
- obj.clause-number: 6.2.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-31707fcc0b704c5: Allgemeines (provision)
Das ist gegeben, wenn der Stromfluss über den menschlichen Körper nicht wahrnehmbar ist.
- bib.al.original-language: de
- bib.dp.publication-date: 2018-07-01
- ids.document: 7104561
- ids.tracing: hash-3EDB24B05B984C8FF820B62298690A2A99E7F2F8758A783C4ABAD945113F2B42
- obj.clause-number: 6.2.1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-65e9b14fca8046d: Allgemeines (provision)
Bei Bränden in abgeschlossenen Betriebsstätten dürfen unter Spannung stehende Anlagenteile nur im Einvernehmen mit dem Anlagenverantwortlichen mit Wasser angespritzt werden.
- bib.al.original-language: de
- bib.dp.publication-date: 2018-07-01
- ids.document: 7104561
- ids.tracing: hash-06CEA12B485E9D71B2DF1F92DCBC64173810BAE87850E92D747F53C411D797EA
- obj.clause-number: 6.2.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-c6d3de824c75431: Allgemeines (provision)
Das Einvernehmen kann auch durch vorherige Absprache hergestellt werden.
- bib.al.original-language: de
- bib.dp.publication-date: 2018-07-01
- ids.document: 7104561
- ids.tracing: hash-21563CEBF7BF2B7572A6DA2560913F7005F9D85A75865C42697A58076CE84DA9
- obj.clause-number: 6.2.1
- obj.element-name: paragraph
- obj.language: de
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

##### prov-7104561-dd4462282bc74b2: Allgemeines (provision)
Sind den Einsatzkräften die anstehenden Spannungen und die örtlichen Verhältnisse zunächst unbekannt, so dürfen beim Einsatz von Strahlrohren CM nach DIN 14365-1 zwischen Strahlrohr und unter Spannung stehenden Anlagenteilen die Richtwerte nach Tabelle 4 nicht unterschritten werden.
- bib.al.original-language: de
- bib.dp.publication-date: 2018-07-01
- ids.document: 7104561
- ids.tracing: hash-ED243E2D8AB339B2BFF5020258A22F0F9CD89A23BA6313C519B8D5911C9F1205
- obj.clause-number: 6.2.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-f97005fc5e22436

##### prov-7104561-572544e6e5a849a: Allgemeines (provision)
Im Zweifelsfall ist immer der höchste Abstand einzuhalten.
- bib.al.original-language: de
- bib.dp.publication-date: 2018-07-01
- ids.document: 7104561
- ids.tracing: hash-6481C5561E486076D7EDC17CD6E1F50093165F0DBC9B937F4BD2B46AC1419D17
- obj.clause-number: 6.2.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-f97005fc5e22436: Richtwerte (provision)
Tabelle 4 — Richtwerte
| Strahlrohr DIN 14365-CM | Niederspannung (N) ≤ AC 1 kV oder ≤ DC 1,5 kV | Hochspannung (H) > AC 1 kV oder > DC 1,5 kV |
| --- | --- | --- |
| Sprühstrahl | 1 m | 5 m |
| Vollstrahl | 5 m | 10 m |
| Kurzzeichen | N-1-5 | H-5-10 |
- bib.al.original-language: de
- bib.dp.publication-date: 2018-07-01
- ids.document: 7104561
- ids.tracing: hash-2539D8C66690D0D9757F2D333B6C62BDA59CD243D011A8AD145B5CA03C25A6D5
- obj.clause-number: Tabelle 4
- obj.element-name: table
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-433c1c5b3efc483: Allgemeines (provision)
In Niederspannungsanlagen gelten diese Richtwerte auch für Feuerlöscher nach DIN EN 3 (alle Teile) und in allen Anlagen auch für größere Wasserlöschgeräte, wenn deren Strahlrohre im Sinne der elektrischen Sicherheit DIN 14365-2:1986-09 entsprechen.
- bib.al.original-language: de
- bib.dp.publication-date: 2018-07-01
- ids.document: 7104561
- ids.tracing: hash-37A32CF84E2D63ADC66394FC9588D740A1AB7090D281DADC40326B960180DAE4
- obj.clause-number: 6.2.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

##### prov-7104561-51e86a6591fd441: Allgemeines (provision)
Die Verwendungs- bzw. Warnhinweise auf den Löschgeräten sind zu beachten.
- bib.al.original-language: de
- bib.dp.publication-date: 2018-07-01
- ids.document: 7104561
- ids.tracing: hash-95E0C0F61545BA1E86B8D498CC233FD74BFD98E9ACDFB761B1A55933E308A5ED
- obj.clause-number: 6.2.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### R269: Wasser (heading)
- bib.al.original-language: de
- bib.dp.publication-date: 2018-07-01
- ids.document: 7104561
- obj.clause-number: 6.2.2
- obj.element-name: heading
- obj.language: de
- obj.specobject-type: heading
- ChapterName: 6.2.2 Wasser

##### prov-7104561-402ce973f12548e: Wasser (provision)
Für den Einsatz von Wasser gilt Tabelle 5.
- bib.al.original-language: de
- bib.dp.publication-date: 2018-07-01
- ids.document: 7104561
- ids.tracing: hash-D05E582DA4B9B5E0DB9CF54E0A435EEA0FD74D25E606D53278F2CBE62EC1DFBD
- obj.clause-number: 6.2.2
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-69867da9b1324e0

##### prov-7104561-69867da9b1324e0: Löschmittel Wassera (provision)
Tabelle 5 — Löschmittel Wasser^a
| Lfd. Nr. | Geräte/Anwendungsform | Wirksame Wurfweite (Mittelwert) m | Eignung für Brandklasse nach DIN EN 2 | Mindestabstände (m) zwischen Löschmittelaustrittsöffnung und unter Spannung stehenden Anlagenteilen |  |  |  |  |
| --- | --- | --- | --- | --- | --- | --- | --- | --- |
| Lfd. Nr. | Geräte/Anwendungsform | Wirksame Wurfweite (Mittelwert) m | Eignung für Brandklasse nach DIN EN 2 | Niederspannung bis | Hochspannung bis AC |  |  |  |
| Lfd. Nr. | Geräte/Anwendungsform | Wirksame Wurfweite (Mittelwert) m | Eignung für Brandklasse nach DIN EN 2 | AC 1 000 V oder DC 1 500 V | 30 kV | 110 kV | 220 kV | 380 kV |
|  | Strahlrohre CM nach DIN 14365-1:1991-02 |  |  |  |  |  |  |  |
| 1a | Sprühstrahl | 5 (bei 5 bar Fließdruck) | A B nur eingeschränkt | 1 | 3^b | 3 | 4 | 5 |
| 1b | Vollstrahl | 10 (bei 5 bar Fließdruck) | A | 5 | 5 | 6 | 7 | 8 |
|  | Strahlrohre nach DIN EN 15182-2 (≤ 235 l/min; C-Kupplung) |  |  |  | ^Eine Gefährdungsbeurteilung ist durchzuführen, ob eine elektrische Prüfung erforderlich ist ^c |  |  |  |
| 2a | Strahlrohre nach Sprühstrahl | 3 bis 5 | A B nur eingeschränkt | 1 | ^Eine Gefährdungsbeurteilung ist durchzuführen, ob eine elektrische Prüfung erforderlich ist ^c |  |  |  |
| 2b | Vollstrahl | > 10 | A | 5 | ^Eine Gefährdungsbeurteilung ist durchzuführen, ob eine elektrische Prüfung erforderlich ist ^c |  |  |  |
| 3 | Tragbare oder fahrbare Feuerlöscher, die die Anforderung nach DIN EN 3-7:2007-10, Abschnitt 9 erfüllen | 2 bis 6 | A bzw. A + B | 1 | ^d |  |  |  |
| 4 | Tragbare oder fahrbare Feuerlöscher, die die Anforderung nach DIN EN 3-7:2007-10, Abschnitt 9 nicht erfüllen | 2 bis 6 | A bzw. A + B | Einsatz nur in spannungsfreien Anlagenteilen | Einsatz nur in spannungsfreien Anlagenteilen |  |  |  |
| - a Bei tragbaren und fahrbaren Feuerlöschern: Wasser auch mit Zusätzen. - b Bei Aufsicht durch elektrotechnisch unterwiesene Personen oder Elektrofachkräfte ist ein Mindestabstand von 2 m zulässig. - c Da DIN EN 15182-1 bis DIN EN 15182-4 keine Angaben zur elektrischen Prüfung enthalten, hat der Unternehmer besondere Sorgfalt nach Betriebssicherheitsverordnung §3 (1) bzw. UVV Feuerwehr, DGUV Vorschrift 49, §29 (2) walten zu lassen. - d Feuerlöscher nach DIN EN 3 (alle Teile) können auch für Hochspannungsanlagen typgeprüft sein. Die Verwendungshinweise auf diesen Löschgeräten sind zu beachten. |  |  |  |  |  |  |  |  |
| Gefahrenhinweise/Einsatzbeschränkungen Brände im Bereich elektrischer Anlagen sollten möglichst mit Sprühstrahl bekämpft werden. Wird bei Strahlrohren CM nach DIN 14365-1 ein Fließdruck von 5 bar überschritten, sind die angegebenen Mindestabstände bei Einsatz in Hochspannungsanlagen um zusätzlich 2 m zu vergrößern. Ist im Sonderfall, der zwischen Anlagenbetreiber und Feuerwehr abzusprechen ist, die Verwendung von Strahlrohren BM nach DIN 14365-1:1991-02 nicht zu vermeiden, erhöhen sich die Mindestabstände: – bei Verwendung mit Mundstück um 5 m; – bei Verwendung ohne Mundstück um 10 m. Die angegebenen bzw. errechneten Mindestabstände gelten auch für andere Strahlrohre, für die mindestens eine gleichhohe elektrische Sicherheit wie nach DIN 14365-2:1986-09 nachgewiesen wurde. Zur Erreichung des Schutzziels nach 6.2.1 kann der Nachweis über erforderliche Mindestabstände auch mit anderen geeigneten Prüfungen erbracht werden. Bei Wasser mit Bestandteilen, welche die Leitfähigkeit erhöhen, wie z. B. Seewasser und dergleichen, ergeben sich keine Veränderungen der Mindestabstände, jedoch ist die Bildung von leitfähigen Überzügen auf Isolatoren möglich. Wasser mit Bestandteilen, welche die Strahleigenschaft verändern, z. B. Netzmittel, darf im Bereich unter Spannung stehender elektrischer Anlagen nur eingesetzt werden, wenn die einzuhaltenden Mindestabstände in Anlehnung an DIN 14365-2:1986-09 als vorbereitende Maßnahme (siehe Abschnitt 4) für diese Anlagen ermittelt worden sind. Sonstige Geräte, wie z. B. Wasserwerfer, Sonderlöscher, dürfen im Bereich unter Spannung stehender elektrischer Anlagen nur eingesetzt werden, wenn die einzuhaltenden Mindestabstände in Anlehnung an DIN 14365-2:1986-09 als vorbereitende Maßnahme (siehe Abschnitt 4) für diese Anlagen ermittelt worden sind. |  |  |  |  |  |  |  |  |
- bib.al.original-language: de
- bib.dp.publication-date: 2018-07-01
- ids.document: 7104561
- ids.tracing: hash-32AC8AD8A41369BDCE4266B4B2229338790457A97E7980F8C184862F1BD0A1C3
- obj.clause-number: Tabelle 5
- obj.element-name: table
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R258
- cross-reference -> R109

###### prov-7104561-e34664ff28d3424: Wasser, Note (provision)
ANMERKUNG:
Siehe Anhang B „Erläuterungen“.
- bib.al.original-language: de
- bib.dp.publication-date: 2018-07-01
- ids.document: 7104561
- ids.tracing: hash-00FDEFF4843D81F06D3429539B96A63CD182663BB92EBED76A6259EC71F8B022
- obj.clause-number: 6.2.2
- obj.element-name: note
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> R333

#### R273: Schaum (heading)
- bib.al.original-language: de
- bib.dp.publication-date: 2018-07-01
- ids.document: 7104561
- obj.clause-number: 6.2.3
- obj.element-name: heading
- obj.language: de
- obj.specobject-type: heading
- ChapterName: 6.2.3 Schaum

##### prov-7104561-524bdb4da462466: Schaum (provision)
Für den Einsatz von Schaum gilt Tabelle 6.
- bib.al.original-language: de
- bib.dp.publication-date: 2018-07-01
- ids.document: 7104561
- ids.tracing: hash-CCC42A62DBD76FC6A6B42AFCA41816B3FE98F2AB923E989E860C92000D60FB86
- obj.clause-number: 6.2.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-286c2354700d493

##### prov-7104561-286c2354700d493: Löschschaum nach DIN EN 1568 (alle Teile) (provision)
Tabelle 6 — Löschschaum nach DIN EN 1568 (alle Teile)
| Lfd.Nr. | Geräte/ Anwendungsform | Wirksame Wurfweite (Mittelwert) m | Eignung für Brandklasse nach DIN EN 2^a | Mindestabstände (m) zwischen Löschmittelaustrittsöffnung und unter Spannung stehenden Anlagenteilen |  |  |  |  |
| --- | --- | --- | --- | --- | --- | --- | --- | --- |
| Lfd.Nr. | Geräte/ Anwendungsform | Wirksame Wurfweite (Mittelwert) m | Eignung für Brandklasse nach DIN EN 2^a | Niederspannung bis | Hochspannung bis AC |  |  |  |
| Lfd.Nr. | Geräte/ Anwendungsform | Wirksame Wurfweite (Mittelwert) m | Eignung für Brandklasse nach DIN EN 2^a | AC 1 000 V oder DC 1 500 V | 30 kV | 110 kV | 220 kV | 380 kV |
| 1 | Tragbare oder fahrbare Feuerlöscher, die die Anforderungen nach DIN EN 3-7:2007-10, Abschnitt 9 erfüllen | 2 bis 6 | A, B | 1 |  |  |  |  |
| 2 | Tragbare oder fahrbare Feuerlöscher, die die Anforderungen nach DIN EN 3-7:2007-10, Abschnitt 9 nicht erfüllen | 2 bis 6 | A, B |  | Einsatz nur in spannungsfreien Anlagenteilen |  |  |  |
| 3 | Sonstige Geräte, z. B. typgeprüfte tragbare Feuerlöscher oder typgeprüfte fahrbare Feuerlöscher | 3 bis 7 | A, B | 3^b |  |  |  |  |
| 4 | Tragbare Schaumstrahlrohre nach DIN EN 16712-3:2015-12 S1/S2/S4/S8 M0,5/M1/M2/M4/M8 | 9/12/20/25 3/4/6/7/10 | A, B A, B |  |  |  |  |  |
| 5 | Schaumstrahlrohre für Werfer-Unterteile nach DIN 14366-2:1984-10 SW10/SW20/SW40 | 35/45/65 | A, B |  |  |  |  |  |
|  | Bei Abgabe von Druckluftschaum: Strahlrohre nach DIN 14365-1:1991-02 oder DIN EN 15182 oder andere Strahlrohre mit Austrittsöffnungen ≤ 25 mm Durchmesser (für alle Strahlrohre gilt: ≤ 235 l/min Wasser-Schaummittelgemisch und C-Kupplung) |  | A, B |  |  |  |  |  |
| 6a | Sprühstrahl | 3 bis 5 |  | 1 |  |  |  |  |
| 6b | Vollstrahl | > 10 |  | 5 |  |  |  |  |
| ^a Die Eignung kann auch die Brandklasse F umfassen. ^b Dies gilt nur für den Einsatz typgeprüfter Löschgeräte und deren Verwendung in elektrischen Anlagen. |  |  |  |  |  |  |  |  |
| Gefahrenhinweise/Einsatzbeschränkungen Eine Gefahr besteht, wenn zwischen der Einsatzkraft und einem unter Spannung stehenden Anlagenteil eine durchgehende Verbindung aus Wasser und/oder Schaum besteht. Niederspannungsanlagen: 1. Schaum: darf grundsätzlich nur in spannungsfreien Anlagen eingesetzt werden; erforderlichenfalls sind auch benachbarte Anlagen spannungsfrei zu machen. Ausgenommen von dieser Beschränkung ist der Einsatz typgeprüfter Löschgeräte und deren Verwendung in elektrischen Anlagen. 2. Druckluftschaum: - keine Gefahr über den Löschmittelstrahl besteht, wenn die Mindestabstände in Zeile 6 eingehalten werden, - anhaftender Schaum an unter Spannung stehenden Teilen führt zu Spannungsverschleppungen, und die Einsatzkräfte können über einen damit in Verbindung stehenden Schaumteppich gefährdet werden (siehe Bild 2). Hochspannungsanlagen: Schaum darf ohne Ausnahmen nur bei spannungsfreien Anlagenteilen eingesetzt werden; erforderlichenfalls sind auch benachbarte Anlagenteile spannungsfrei zu machen, denn es besteht ansonsten die Gefahr der explosionsartigen Zerstörung der elektrischen Anlage (einhergehend mit z. B. herumfliegenden Teilen und Druckwellen) mit zusätzlicher Gefährdung der Einsatzkräfte. |  |  |  |  |  |  |  |  |
- bib.al.original-language: de
- bib.dp.publication-date: 2018-07-01
- ids.document: 7104561
- ids.tracing: hash-A58B5F5AB2C3342BF072D32BA0E86585F8DCD1398B4329B4CCC42CEDD04489D8
- obj.clause-number: Tabelle 6
- obj.element-name: table
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-9b603ff400844d4

##### prov-7104561-9b603ff400844d4: Schaum (provision)
Bild 2 — Gefährdung der Einsatzkraft durch Spannungsverschleppung über Schaumteppich
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Legende
- bib.al.original-language: de
- bib.dp.publication-date: 2018-07-01
- ids.document: 7104561
- ids.tracing: hash-F1AB0C420B98FF019235490320EC0A51A55C6FC608E4F300D79C7AA4615797BB
- obj.clause-number: 6.2.3
- obj.element-name: figure
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### R277: Pulver (heading)
- bib.al.original-language: de
- bib.dp.publication-date: 2018-07-01
- ids.document: 7104561
- obj.clause-number: 6.2.4
- obj.element-name: heading
- obj.language: de
- obj.specobject-type: heading
- ChapterName: 6.2.4 Pulver

##### prov-7104561-0116e743ae274f5: Pulver (provision)
Für den Einsatz von Pulver gilt Tabelle 7.
- bib.al.original-language: de
- bib.dp.publication-date: 2018-07-01
- ids.document: 7104561
- ids.tracing: hash-19C72291632B40F9B960356E0D28E3289ADF313AEEBC0EA2EDDE05DC530D8BA5
- obj.clause-number: 6.2.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-d8bfa09646f9424

##### prov-7104561-d8bfa09646f9424: Löschpulver nach DIN EN 615 (provision)
Tabelle 7 — Löschpulver nach DIN EN 615
| Lfd.Nr. | Geräte/ Anwendungsform | Wirksame Wurfweite (Mittelwert) m | Eignung für Brandklasse nach DIN EN 2 | Mindestabstände (m) zwischen Löschmittelaustrittsöffnung und unter Spannung stehenden Anlagenteilen |  |  |  |  |
| --- | --- | --- | --- | --- | --- | --- | --- | --- |
| Lfd.Nr. | Geräte/ Anwendungsform | Wirksame Wurfweite (Mittelwert) m | Eignung für Brandklasse nach DIN EN 2 | Niederspannung bis | Hochspannung bis AC |  |  |  |
| Lfd.Nr. | Geräte/ Anwendungsform | Wirksame Wurfweite (Mittelwert) m | Eignung für Brandklasse nach DIN EN 2 | AC 1 000 V oder DC 1 500 V | 30 kV | 110 kV | 220 kV | 380 kV |
| 1 | Tragbare Feuerlöscher nach DIN EN 3 (alle Teile) |  | B, C | 1 | 3^a | 3 | 4 | 5 |
| 1 | Tragbare Feuerlöscher nach DIN EN 3 (alle Teile) | 2 bis 6 | A, B, C | 1 | Einsatz nur in spannungsfreien Anlagenteilen |  |  |  |
| 1 | Tragbare Feuerlöscher nach DIN EN 3 (alle Teile) | 0 bis 1 | D | 1 | Einsatz nur in spannungsfreien Anlagenteilen |  |  |  |
| 2 | Sonstige Geräte, z. B. fahrbare Feuerlöscher | 6 bis 10 | B, C | 1 | 3^a | 3 | 4 | 5 |
| 2 | Sonstige Geräte, z. B. fahrbare Feuerlöscher |  | A, B, C | 1 | Einsatz nur in spannungsfreien Anlagenteilen |  |  |  |
| ^a Bei Aufsicht durch elektrotechnisch unterwiesene Personen oder Elektrofachkräfte ist ein Mindestabstand von 2 m zulässig. |  |  |  |  |  |  |  |  |
| Gefahrenhinweise/Einsatzbeschränkungen Der Einsatz von Löschpulver in elektrischen Anlagen und in deren Nähe darf nur mit Zustimmung des Anlagenbetreibers erfolgen. Beim Einsatz von Löschpulver ist zu beachten: Unter Einfluss von Temperatur, Nässe und Luftfeuchte können Löschpulverbeläge auf Isolatoren in einem Maße leitfähig werden, dass unter Einfluss höherer elektrischer Feldstärken, d. h. im Allgemeinen bei Hochspannung, kurzschlussartige Ströme zum Fließen kommen. Die dadurch entstehenden Störlichtbögen stellen eine Lebensgefahr für sich in der Nähe aufhaltende Personen und eine Gefährdung der Anlage dar. Aus diesem Grunde dürfen Löschpulver in Freiluft- und Innenraumanlagen nur angewendet werden, wenn diese Anlagen trocken sind. Die geforderten Mindestabstände zwischen Löschmittelaustrittsöffnung und unter Spannung stehenden Teilen der elektrischen Anlage dienen der Sicherheit des den Löscheinsatz durchführenden Personals vor direkten Stromeinwirkungen während des Löscheinsatzes. Leitfähige Beläge können in Hochspannungsanlagen Personen und die Anlagen selbst gefährden. Sie sind deshalb nach Möglichkeit zu vermeiden. Es sollten außerdem nur Löschpulver verwendet werden, die keine schwer zu reinigenden Beläge (z. B. Schmelzbeläge bei ABC-Pulver) auf den Anlagenteilen bilden. Der Einsatz von Löschpulver ist im Bereich staubempfindlicher Anlagen (wie Fernmeldeanlagen, Informationsverarbeitungsanlagen, Mess- und Regelanlagen, Verteilerschränken mit Schützen und Relais usw.) zu vermeiden. |  |  |  |  |  |  |  |  |
- bib.al.original-language: de
- bib.dp.publication-date: 2018-07-01
- ids.document: 7104561
- ids.tracing: hash-DDAF1298F63AB996750ACD427D5ABC822A45545A4E6C86DEC88FD42C4242D225
- obj.clause-number: Tabelle 7
- obj.element-name: table
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### R280: Kohlenstoffdioxid (heading)
- bib.al.original-language: de
- bib.dp.publication-date: 2018-07-01
- ids.document: 7104561
- obj.clause-number: 6.2.5
- obj.element-name: heading
- obj.language: de
- obj.specobject-type: heading
- ChapterName: 6.2.5 Kohlenstoffdioxid

##### prov-7104561-d84aed3feeb44c8: Kohlenstoffdioxid (provision)
Für den Einsatz von Kohlenstoffdioxid gilt Tabelle 8.
- bib.al.original-language: de
- bib.dp.publication-date: 2018-07-01
- ids.document: 7104561
- ids.tracing: hash-AD32C11062BF8D4353D2F098C982C10C9DB80DF7B491C3D832720F95441E157A
- obj.clause-number: 6.2.5
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> prov-7104561-e1f4712221c14a5

##### prov-7104561-e1f4712221c14a5: Löschmittel Kohlenstoffdioxid (CO2) (provision)
Tabelle 8 — Löschmittel Kohlenstoffdioxid (CO_2)
| Lfd.Nr. | Geräte/ Anwendungsform | Wirksame Wurfweite (Mittelwert) m | Eignung für Brandklasse nach DIN EN 2 | Mindestabstände (m) zwischen Löschmittelaustrittsöffnung und unter Spannung stehenden Anlagenteilen |  |  |  |  |
| --- | --- | --- | --- | --- | --- | --- | --- | --- |
| Lfd.Nr. | Geräte/ Anwendungsform | Wirksame Wurfweite (Mittelwert) m | Eignung für Brandklasse nach DIN EN 2 | Niederspannung bis | Hochspannung bis AC |  |  |  |
| Lfd.Nr. | Geräte/ Anwendungsform | Wirksame Wurfweite (Mittelwert) m | Eignung für Brandklasse nach DIN EN 2 | AC 1 000 V oder DC 1 500 V | 30 kV | 110 kV | 220 kV | 380 kV |
| 1 | Tragbare Feuerlöscher nach DIN EN 3 (alle Teile) | 2 bis 3 | B | 1 | 3^a | 3 | 4 | 5 |
| 2 | Sonstige Geräte, z. B. fahrbare Feuerlöscher | 3 bis 4 | B |  |  |  |  |  |
| - a Bei Aufsicht durch elektrotechnisch unterwiesene Personen oder Elektrofachkräfte ist ein Mindestabstand von 2 m zulässig. |  |  |  |  |  |  |  |  |
| Gefahrenhinweise/Einsatzbeschränkungen Kohlenstoffdioxid ist elektrisch nichtleitend und hinterlässt keine Rückstände. Die Anwendung ist bei unter Spannung stehenden Anlagen unbedenklich, wenn die Mindestabstände eingehalten werden. Kohlenstoffdioxid ist schwerer als Luft, ist ab 5 % Volumenanteilen gesundheitsgefährdend und wirkt ab 8 % lebensbedrohlich. Vorsicht bei Verwendung in engen, schlecht belüfteten Räumen. Lebensgefahr! Gefahrenhinweise auf den Löschgeräten beachten. In Außenanlagen ist die Wirkung begrenzt, weil sich Kohlenstoffdioxid verflüchtigt. |  |  |  |  |  |  |  |  |
- bib.al.original-language: de
- bib.dp.publication-date: 2018-07-01
- ids.document: 7104561
- ids.tracing: hash-E4FFBB95460DA48637C5B41E2CE3C3C8CEF6A4AC66E2F0D3D5B7C932C3442243
- obj.clause-number: Tabelle 8
- obj.element-name: table
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

## R283: Maßnahmen nach einem Brand (heading)
- bib.al.original-language: de
- bib.dp.publication-date: 2018-07-01
- ids.document: 7104561
- obj.clause-number: 7
- obj.element-name: heading
- obj.language: de
- obj.specobject-type: heading
- ChapterName: 7 Maßnahmen nach einem Brand

### R284: 7.1 (heading)
- bib.al.original-language: de
- bib.dp.publication-date: 2018-07-01
- ids.document: 7104561
- obj.element-name: heading
- obj.language: de
- obj.specobject-type: heading

#### prov-7104561-d36a6e55dc614b6 (provision)
Beim Betreten der Brandstelle ist besondere Vorsicht erforderlich.
- bib.al.original-language: de
- bib.dp.publication-date: 2018-07-01
- ids.document: 7104561
- ids.tracing: hash-0705F4B4D11E7F5844926D02FA5C996267E55CA480311B5DB4EEE7AC19967FA4
- obj.clause-number: 7.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### R286: 7.2 (heading)
- bib.al.original-language: de
- bib.dp.publication-date: 2018-07-01
- ids.document: 7104561
- obj.element-name: heading
- obj.language: de
- obj.specobject-type: heading

#### prov-7104561-6c6b09b28bbd404 (provision)
Es besteht die Gefahr, dass vorhandene Metallteile unter Spannung stehen können, also nicht nur elektrische Leitungen und Geräte, sondern auch metallene Rohrleitungen, Dachrinnen oder Drahtzäune, sofern sie mit unter Spannung stehenden Anlagenteilen in Berührung stehen.
- bib.al.original-language: de
- bib.dp.publication-date: 2018-07-01
- ids.document: 7104561
- ids.tracing: hash-56FAA0AADF4546411B95C238B0E323F2EDA384548AF1A6A3F88650FCC6298E4F
- obj.clause-number: 7.2
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### R288: 7.3 (heading)
- bib.al.original-language: de
- bib.dp.publication-date: 2018-07-01
- ids.document: 7104561
- obj.element-name: heading
- obj.language: de
- obj.specobject-type: heading

#### prov-7104561-9a985612bd0b46c (provision)
Nach dem Brand ist der Brandraum zu lüften, bevor Personen ohne Atemschutz den Raum betreten, wobei zu vermeiden ist, dass sich giftige und korrosive Zersetzungsprodukte im Gebäude ausbreiten (siehe 5.1.7).
- bib.al.original-language: de
- bib.dp.publication-date: 2018-07-01
- ids.document: 7104561
- ids.tracing: hash-B99E21D903C0EFE4C86CC840467956C6AF26062CA12277F9BC1A8A2B04866472
- obj.clause-number: 7.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R181

#### prov-7104561-2d383d7c88dc4b5 (provision)
Unbefugte Personen dürfen die Brandstelle nicht betreten.
- bib.al.original-language: de
- bib.dp.publication-date: 2018-07-01
- ids.document: 7104561
- ids.tracing: hash-C8A3026B4B2191D9A18409247FE7119EC7920FF2446036422B037157B6CA05A0
- obj.clause-number: 7.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### R291: 7.4 (heading)
- bib.al.original-language: de
- bib.dp.publication-date: 2018-07-01
- ids.document: 7104561
- obj.element-name: heading
- obj.language: de
- obj.specobject-type: heading

#### prov-7104561-47dbd5d014b1414 (provision)
Besteht Verdacht, dass Personen mit giftigen Zersetzungsprodukten in Kontakt gekommen sind, müssen sie unverzüglich fachärztlicher Betreuung zugeführt werden.
- bib.al.original-language: de
- bib.dp.publication-date: 2018-07-01
- ids.document: 7104561
- ids.tracing: hash-3E477E47AABA33DFDCE932C946387389AE158BE1B7DB59D6EA7373100B3A561C
- obj.clause-number: 7.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### R293: 7.5 (heading)
- bib.al.original-language: de
- bib.dp.publication-date: 2018-07-01
- ids.document: 7104561
- obj.element-name: heading
- obj.language: de
- obj.specobject-type: heading

#### prov-7104561-dec19149a42d409 (provision)
Unter Spannung stehende elektrische Anlagenteile sind gegen direktes Berühren zu sichern, siehe DIN VDE 0105-100 (VDE 0105-100) .
- bib.al.original-language: de
- bib.dp.publication-date: 2018-07-01
- ids.document: 7104561
- ids.tracing: hash-7A6BA69319A87F42A09FE25F59F24696547DDD687868D890A21AE76900C7E8F0
- obj.clause-number: 7.5
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> pkn--3011489

### R295: 7.6 (heading)
- bib.al.original-language: de
- bib.dp.publication-date: 2018-07-01
- ids.document: 7104561
- obj.element-name: heading
- obj.language: de
- obj.specobject-type: heading

#### prov-7104561-6e585f9b3fb64a4 (provision)
Pulverbeläge auf Isolatoren können zu Schäden führen und sollten möglichst bald nach Beendigung der Löscharbeiten beseitigt werden.
- bib.al.original-language: de
- bib.dp.publication-date: 2018-07-01
- ids.document: 7104561
- ids.tracing: hash-04857D617B2005C160DA7353463FA4603724190DA9EFDAF1C43AD96664219D5C
- obj.clause-number: 7.6
- obj.element-name: paragraph
- obj.language: de
- obj.modality: recommendation
- obj.normativity: normative
- obj.specobject-type: provision
- use.business-process: undefined
- use.business-sector: undefined
- use.interaction: undefined
- use.location: undefined
- use.product-category: undefined
- use.product-life-cycle: undefined
- use.project-phase: undefined
- use.purpose: undefined

### R297: 7.7 (heading)
- bib.al.original-language: de
- bib.dp.publication-date: 2018-07-01
- ids.document: 7104561
- obj.element-name: heading
- obj.language: de
- obj.specobject-type: heading

#### prov-7104561-86a3d7ab6b904c4 (provision)
Die Freigabe oder gegebenenfalls die Wiederinbetriebnahme elektrischer Anlagen darf in Hochspannungsanlagen nur durch den Anlagenverantwortlichen erfolgen.
- bib.al.original-language: de
- bib.dp.publication-date: 2018-07-01
- ids.document: 7104561
- ids.tracing: hash-104081C85F6006B9FBD6F966FE95566F55021B1E6FBF91F9AC671AD7B44E6BBC
- obj.clause-number: 7.7
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

## R299: Erste Maßnahmen bei Unfällen durch elektrischen Strom (heading)
- bib.al.original-language: de
- bib.dp.publication-date: 2018-07-01
- ids.document: 7104561
- obj.clause-number: 8
- obj.element-name: heading
- obj.language: de
- obj.specobject-type: heading
- ChapterName: 8 Erste Maßnahmen bei Unfällen durch elektrischen Strom

### prov-7104561-c3126b10ad93474: Erste Maßnahmen bei Unfällen durch elektrischen Strom (provision)
Für Erste-Hilfe-Maßnahmen siehe DGUV Information 204-006 „Anleitung zur Ersten Hilfe“ und DGUV Fachinformation „Stromunfall - Ärztliche Vorstellung notwendig“.
- bib.al.original-language: de
- bib.dp.publication-date: 2018-07-01
- ids.document: 7104561
- ids.tracing: hash-5C257EDFFB65ED08149EBC9F026729B4D4636B088EF1B9BCF5197A938277F056
- obj.clause-number: 8
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

### R301: 8.1 (heading)
- bib.al.original-language: de
- bib.dp.publication-date: 2018-07-01
- ids.document: 7104561
- obj.element-name: heading
- obj.language: de
- obj.specobject-type: heading

#### prov-7104561-9a9ff3cf73a841a (provision)
Beim Berühren von unter Spannung stehenden Teilen besteht Lebensgefahr.
- bib.al.original-language: de
- bib.dp.publication-date: 2018-07-01
- ids.document: 7104561
- ids.tracing: hash-45FCDF51E2F179B0D8C6494C8B4521C50DAF21B486EF754609A8823215C3DF0C
- obj.clause-number: 8.1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-adec9bb002f2495 (provision)
Außer Verbrennungen kann der elektrische Strom eine Muskelverkrampfung, die zur Atemlähmung führen kann, und Herzkammerflimmern verursachen.
- bib.al.original-language: de
- bib.dp.publication-date: 2018-07-01
- ids.document: 7104561
- ids.tracing: hash-A017F8C3F7EABA6BA7D69F75D3311D80D3A9F90A9CFC9E7410F354AB02B5D48A
- obj.clause-number: 8.1
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-b25ff67acf664d3 (provision)
Ein Verunglückter ist so schnell wie möglich von der Spannung zu trennen (siehe 8.2 und 8.3).
- bib.al.original-language: de
- bib.dp.publication-date: 2018-07-01
- ids.document: 7104561
- ids.tracing: hash-C2238A17DF8CE9A2AA7E2CCF143030701C624EC5E52CF58C642A70F91D4FC1A7
- obj.clause-number: 8.1
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R305
- cross-reference -> R309

### R305: 8.2 (heading)
- bib.al.original-language: de
- bib.dp.publication-date: 2018-07-01
- ids.document: 7104561
- obj.element-name: heading
- obj.language: de
- obj.specobject-type: heading

#### prov-7104561-62a25702797f491 (provision)
In Niederspannungsanlagen ist zunächst die betreffende Leitung spannungsfrei zu machen, da eine vorherige Berührung des Verunglückten den Helfer selbst gefährdet.
- bib.al.original-language: de
- bib.dp.publication-date: 2018-07-01
- ids.document: 7104561
- ids.tracing: hash-DD08B174F52EF7519E466DAA51B8CD5CF367436E56D1CE61EB7C9F7DC0ADA47C
- obj.clause-number: 8.2
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-56055b7faece4cb (provision)
Ist dies nicht möglich, dann kann man den Verunglückten von gut isoliertem Standort aus (trockenes Holz, trockene Kleider) von den Leitungen oder Geräten wegziehen.
- bib.al.original-language: de
- bib.dp.publication-date: 2018-07-01
- ids.document: 7104561
- ids.tracing: hash-45827734DCD292C4011F9DF1F4E17ECCCFF2A3D6254292BE5B58CC43E23068F4
- obj.clause-number: 8.2
- obj.element-name: paragraph
- obj.language: de
- obj.modality: permission
- obj.normativity: normative
- obj.specobject-type: provision
- obj.transformation-issues: Possibly wrong modal verb
- use.business-process: undefined
- use.business-sector: undefined
- use.interaction: undefined
- use.location: undefined
- use.product-category: undefined
- use.product-life-cycle: undefined
- use.project-phase: undefined
- use.purpose: undefined

#### prov-7104561-381303cce9e6461 (provision)
Dabei darf man unbedeckte Körperteile nicht mit ungeschützten Händen berühren, sondern muss sich z. B. trockener Decken, Kleider, Handschuhe, Holzlatten bedienen.
- bib.al.original-language: de
- bib.dp.publication-date: 2018-07-01
- ids.document: 7104561
- ids.tracing: hash-BAA810684DDB3C7F938ED417C0DAF6E939AA34EDBED0065F42A78D0F90A4447B
- obj.clause-number: 8.2
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

### R309: 8.3 (heading)
- bib.al.original-language: de
- bib.dp.publication-date: 2018-07-01
- ids.document: 7104561
- obj.element-name: heading
- obj.language: de
- obj.specobject-type: heading

#### prov-7104561-b86916b3bf7147d (provision)
Bei Hochspannungsanlagen dürfen nur Elektrofachkräfte und elektrotechnisch unterwiesene Personen eingreifen.
- bib.al.original-language: de
- bib.dp.publication-date: 2018-07-01
- ids.document: 7104561
- ids.tracing: hash-1CD92876B6CAD0F9F40A2EF79779DAC5BA00FFC53D987FF4E476A4D9DCFA89C5
- obj.clause-number: 8.3
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-3424b88429ca49c (provision)
Auch die Annäherung (siehe 5.3.4 und 5.3.5) an den Verunglückten ist gefährlich.
- bib.al.original-language: de
- bib.dp.publication-date: 2018-07-01
- ids.document: 7104561
- ids.tracing: hash-A6426901D88B1D6E1DD21FFC5D471ADB3D29D498AE89599D3BE63277989D04CD
- obj.clause-number: 8.3
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined
- cross-reference -> R212
- cross-reference -> R219

### R312: 8.4 (heading)
- bib.al.original-language: de
- bib.dp.publication-date: 2018-07-01
- ids.document: 7104561
- obj.element-name: heading
- obj.language: de
- obj.specobject-type: heading

#### prov-7104561-ab3e45bad3844ae (provision)
Brennende Personen sind am Fortlaufen zu hindern und notfalls am Boden zu wälzen.
- bib.al.original-language: de
- bib.dp.publication-date: 2018-07-01
- ids.document: 7104561
- ids.tracing: hash-28319E8D636A7C9F783322EF9DFF9D75BBB745F0312573322DB58E8D769DB0E9
- obj.clause-number: 8.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-b86d764a3f8d46c (provision)
Zum Ablöschen brennender Kleidung an Personen eignen sich insbesondere Wasser, Feuerlöscher oder Löschdecken.
- bib.al.original-language: de
- bib.dp.publication-date: 2018-07-01
- ids.document: 7104561
- ids.tracing: hash-FB041F0B87257AA2033E08E09FE6CB08F5E9F19B26861BB0106999DD4B04C123
- obj.clause-number: 8.4
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-13e6e0d874134cd (provision)
Auch das Einhüllen mit anderen Decken, ausgenommen brennbare Kunststoffdecken, kann helfen.
- bib.al.original-language: de
- bib.dp.publication-date: 2018-07-01
- ids.document: 7104561
- ids.tracing: hash-BC69086C340C9E5715B6D59AC77F90C027DFEA30BAB04E4F22D78C6C6D5EE0CE
- obj.clause-number: 8.4
- obj.element-name: paragraph
- obj.language: de
- obj.modality: undefined
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-dbc8a66627e246d (provision)
Es können auch andere Löschmittel eingesetzt werden, wenn nur damit schnell gelöscht werden kann, da dies als Rettungsmaßnahme Vorrang vor anderen Überlegungen haben muss.
- bib.al.original-language: de
- bib.dp.publication-date: 2018-07-01
- ids.document: 7104561
- ids.tracing: hash-009C213C37F1BE8DD18441BC3862E679C598D5CCD0DA67D4C6EA472082ABC301
- obj.clause-number: 8.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

#### prov-7104561-d1e406df3fae4a4 (provision)
Wurden andere Löschmittel als Wasser eingesetzt, so ist dies dem erstversorgenden Arzt oder dem Rettungsdienstpersonal mitzuteilen.
- bib.al.original-language: de
- bib.dp.publication-date: 2018-07-01
- ids.document: 7104561
- ids.tracing: hash-A729F7E4709B5597CDF0560A8D4CB6C20C8946960C704BF0DE60BF17C072F45C
- obj.clause-number: 8.4
- obj.element-name: paragraph
- obj.language: de
- obj.modality: requirement
- obj.normativity: normative
- obj.specobject-type: provision
- use.business-process: undefined
- use.business-sector: undefined
- use.interaction: undefined
- use.location: undefined
- use.product-category: undefined
- use.product-life-cycle: undefined
- use.project-phase: undefined
- use.purpose: undefined

## R318: Beurteilung von Gefahren, die von PCB-haltigen Betriebsmitteln ausgehen können (heading)
- bib.al.original-language: de
- bib.dp.publication-date: 2018-07-01
- ids.document: 7104561
- obj.clause-number: Anhang A
- obj.element-name: heading
- obj.language: de
- obj.specobject-type: heading
- ChapterName: Anhang A Beurteilung von Gefahren, die von PCB-haltigen Betriebsmitteln ausgehen können

### prov-7104561-8eb62e6007c9470: Beurteilung von Gefahren, die von PCB-haltigen Betriebsmitteln ausgehen können (provision)
Bei der Beurteilung der Gefahren, die von PCB-haltigen Betriebsmitteln ausgehen können, ist zu unterscheiden:
- Gefährlichkeit der polychlorierten Biphenyle (PCB) bei Brandeinwirkung.
Aus höher chlorierten Biphenylen können sich Spuren giftiger Zersetzungsprodukte bilden (Dibenzodioxin- und Dibenzofuran-Verbindungen).
Maßnahmen: Die Entstehung der Zersetzungsprodukte muss durch raschen und energischen Löschangriff, gegebenenfalls durch Kühlung der PCB-haltigen Betriebsmittel, vermieden werden. Dabei gewähren die Feuerwehreinsatzkleidung, umluftunabhängiger Atemschutz und Kontaminationsschutzhaube ausreichende Sicherheit für die Einsatzkräfte. Besondere Vollschutzanzüge sind unter anderem wegen ihrer geringen thermischen Widerstandsfähigkeit und vor allem wegen der physiologischen Belastung des Personals bei Brandbekämpfung im Innenangriff ungeeignet.
- Gefährlichkeit der polychlorierten Biphenyle (PCB) ohne Brandeinwirkung.
PCB sind nach der Gefahrstoffverordnung als gesundheitsschädlich und umweltgefährdend eingestuft (Andreaskreuz, Xn, N bzw. GHS 08). Wegen ihrer hohen Stabilität sind sie jedoch schwer abbaubar, sie dürfen daher nicht ins Erdreich gelangen.
Maßnahmen: Ausgelaufene Flüssigkeit ist in Behältern aufzufangen oder mit Bindemitteln aufzunehmen und als gefährlicher Abfall zu entsorgen. Es sind Chemikalienschutzhandschuhe zu tragen, gegebenenfalls ist Atemschutz anzulegen; Hautkontakt ist zu vermeiden.
- Waren beim Brand PCB-haltige Betriebsmittel (siehe 4.1.2) beteiligt, ist die Brandstelle zu sperren und zu sichern. Schutzkleidung der Einsatzkräfte und Geräte, die im Einsatz waren, sind an einem Sammelplatz zu lagern. Weitere Maßnahmen sind abhängig von dem Ergebnis der Kontaminationsprüfung.
- bib.al.original-language: de
- bib.dp.publication-date: 2018-07-01
- ids.document: 7104561
- ids.tracing: hash-06239968689E7624AE1A6D21868BF729D9473B31E6E555EFE48660AB9ACFCE72
- obj.clause-number: Anhang A
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-7104561-4077ba0def5447b: Beurteilung von Gefahren, die von PCB-haltigen Betriebsmitteln ausgehen können (provision)
Bei der Beurteilung der Gefahren, die von PCB-haltigen Betriebsmitteln ausgehen können, ist zu unterscheiden:
- Gefährlichkeit der polychlorierten Biphenyle (PCB) bei Brandeinwirkung.
- bib.al.original-language: de
- bib.dp.publication-date: 2018-07-01
- ids.document: 7104561
- ids.tracing: hash-CC9CF717FE796F80F147E8FCAD9E948E7212AA379811C5B1E008170A45DD1F4C
- obj.clause-number: Anhang A
- obj.element-name: paragraph
- obj.language: de
- obj.modality: requirement
- obj.normativity: informative
- obj.specobject-type: provision
- use.business-process: undefined
- use.business-sector: undefined
- use.interaction: undefined
- use.location: undefined
- use.product-category: undefined
- use.product-life-cycle: undefined
- use.project-phase: undefined
- use.purpose: undefined

### prov-7104561-b54b71a0c947434: Beurteilung von Gefahren, die von PCB-haltigen Betriebsmitteln ausgehen können, list extract (provision)
Aus höher chlorierten Biphenylen können sich Spuren giftiger Zersetzungsprodukte bilden (Dibenzodioxin- und Dibenzofuran-Verbindungen).
- bib.al.original-language: de
- bib.dp.publication-date: 2018-07-01
- ids.document: 7104561
- ids.tracing: hash-2F79893762DBE5E706F0A85444F501360D420EAC36E9D5282CC23946679F88FB
- obj.clause-number: Anhang A
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-7104561-8ba0a3df033943c: Beurteilung von Gefahren, die von PCB-haltigen Betriebsmitteln ausgehen können, list extract (provision)
Maßnahmen: Die Entstehung der Zersetzungsprodukte muss durch raschen und energischen Löschangriff, gegebenenfalls durch Kühlung der PCB-haltigen Betriebsmittel, vermieden werden.
- bib.al.original-language: de
- bib.dp.publication-date: 2018-07-01
- ids.document: 7104561
- ids.tracing: hash-C4B7553EA9A2F4C97AE3687DE3C5C946DE72E0377DE2E660975C1545CCD261BE
- obj.clause-number: Anhang A
- obj.element-name: paragraph
- obj.language: de
- obj.modality: requirement
- obj.normativity: informative
- obj.specobject-type: provision
- use.business-process: undefined
- use.business-sector: undefined
- use.interaction: undefined
- use.location: undefined
- use.product-category: undefined
- use.product-life-cycle: undefined
- use.project-phase: undefined
- use.purpose: undefined

### prov-7104561-3b634dafe3024e9: Beurteilung von Gefahren, die von PCB-haltigen Betriebsmitteln ausgehen können, list extract (provision)
Dabei gewähren die Feuerwehreinsatzkleidung, umluftunabhängiger Atemschutz und Kontaminationsschutzhaube ausreichende Sicherheit für die Einsatzkräfte.
- bib.al.original-language: de
- bib.dp.publication-date: 2018-07-01
- ids.document: 7104561
- ids.tracing: hash-FF90E6C5CE42D680D269A1ADD7C3D6BD058768A4DC1DD7DF8BE18415756F7F50
- obj.clause-number: Anhang A
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-7104561-2f1f3991a0164a3: Beurteilung von Gefahren, die von PCB-haltigen Betriebsmitteln ausgehen können, list extract (provision)
Besondere Vollschutzanzüge sind unter anderem wegen ihrer geringen thermischen Widerstandsfähigkeit und vor allem wegen der physiologischen Belastung des Personals bei Brandbekämpfung im Innenangriff ungeeignet.
- bib.al.original-language: de
- bib.dp.publication-date: 2018-07-01
- ids.document: 7104561
- ids.tracing: hash-0AB47521B43D7D5A62405E47CCA4E090C507DA1DE6670CD11613233EF4A496C9
- obj.clause-number: Anhang A
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-7104561-5a02262e01d04af: Beurteilung von Gefahren, die von PCB-haltigen Betriebsmitteln ausgehen können, list extract (provision)
Gefährlichkeit der polychlorierten Biphenyle (PCB) ohne Brandeinwirkung.
- bib.al.original-language: de
- bib.dp.publication-date: 2018-07-01
- ids.document: 7104561
- ids.tracing: hash-93B30E70991EBEAB7E9F279C69F967A2B325041E3D22BC173EA886682AE212C1
- obj.clause-number: Anhang A
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-7104561-5dc3400d6139415: Beurteilung von Gefahren, die von PCB-haltigen Betriebsmitteln ausgehen können, list extract (provision)
PCB sind nach der Gefahrstoffverordnung als gesundheitsschädlich und umweltgefährdend eingestuft (Andreaskreuz, Xn, N bzw. GHS 08).
- bib.al.original-language: de
- bib.dp.publication-date: 2018-07-01
- ids.document: 7104561
- ids.tracing: hash-E9A17F14D08386042EC3E318D5111F6CA5BD1A107C024978088798B3DB8AEAF6
- obj.clause-number: Anhang A
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-7104561-94fa4513f28c48d: Beurteilung von Gefahren, die von PCB-haltigen Betriebsmitteln ausgehen können, list extract (provision)
Wegen ihrer hohen Stabilität sind sie jedoch schwer abbaubar, sie dürfen daher nicht ins Erdreich gelangen.
- bib.al.original-language: de
- bib.dp.publication-date: 2018-07-01
- ids.document: 7104561
- ids.tracing: hash-C37D7CCF92C36E9C2E54544F382B568CC7AD91F2901C1BFF98705B4A275086C7
- obj.clause-number: Anhang A
- obj.element-name: paragraph
- obj.language: de
- obj.modality: requirement
- obj.normativity: informative
- obj.specobject-type: provision
- use.business-process: undefined
- use.business-sector: undefined
- use.interaction: undefined
- use.location: undefined
- use.product-category: undefined
- use.product-life-cycle: undefined
- use.project-phase: undefined
- use.purpose: undefined

### prov-7104561-756407af21f2470: Beurteilung von Gefahren, die von PCB-haltigen Betriebsmitteln ausgehen können, list extract (provision)
Maßnahmen: Ausgelaufene Flüssigkeit ist in Behältern aufzufangen oder mit Bindemitteln aufzunehmen und als gefährlicher Abfall zu entsorgen.
- bib.al.original-language: de
- bib.dp.publication-date: 2018-07-01
- ids.document: 7104561
- ids.tracing: hash-5902F9206858258F56B33537387E4F5DCD24BD1AF473524F978D14B143E91506
- obj.clause-number: Anhang A
- obj.element-name: paragraph
- obj.language: de
- obj.modality: requirement
- obj.normativity: informative
- obj.specobject-type: provision
- use.business-process: undefined
- use.business-sector: undefined
- use.interaction: undefined
- use.location: undefined
- use.product-category: undefined
- use.product-life-cycle: undefined
- use.project-phase: undefined
- use.purpose: undefined

### prov-7104561-a01b2dacf1464eb: Beurteilung von Gefahren, die von PCB-haltigen Betriebsmitteln ausgehen können, list extract (provision)
Es sind Chemikalienschutzhandschuhe zu tragen, gegebenenfalls ist Atemschutz anzulegen; Hautkontakt ist zu vermeiden.
- bib.al.original-language: de
- bib.dp.publication-date: 2018-07-01
- ids.document: 7104561
- ids.tracing: hash-1C629472F6C23086FA684C5C960369A5F94EBF84DBE0FAEB78FF58BF05C7AE77
- obj.clause-number: Anhang A
- obj.element-name: paragraph
- obj.language: de
- obj.modality: requirement
- obj.normativity: informative
- obj.specobject-type: provision
- use.business-process: undefined
- use.business-sector: undefined
- use.interaction: undefined
- use.location: undefined
- use.product-category: undefined
- use.product-life-cycle: undefined
- use.project-phase: undefined
- use.purpose: undefined

### prov-7104561-e9f8c0a742de48b: Beurteilung von Gefahren, die von PCB-haltigen Betriebsmitteln ausgehen können, list extract (provision)
Waren beim Brand PCB-haltige Betriebsmittel (siehe 4.1.2) beteiligt, ist die Brandstelle zu sperren und zu sichern.
- bib.al.original-language: de
- bib.dp.publication-date: 2018-07-01
- ids.document: 7104561
- ids.tracing: hash-D8D69FF333A522C76FCD9B00566F1F28A06F5293BDEF3DE6C90372B7DCEB427D
- obj.clause-number: Anhang A
- obj.element-name: paragraph
- obj.language: de
- obj.modality: requirement
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> R116

### prov-7104561-6e892ed189e9408: Beurteilung von Gefahren, die von PCB-haltigen Betriebsmitteln ausgehen können, list extract (provision)
Schutzkleidung der Einsatzkräfte und Geräte, die im Einsatz waren, sind an einem Sammelplatz zu lagern.
- bib.al.original-language: de
- bib.dp.publication-date: 2018-07-01
- ids.document: 7104561
- ids.tracing: hash-D6E404D63CE923BDAF21F35A17C40BAD8717E1B7BE88CC757E624CF02E9024FC
- obj.clause-number: Anhang A
- obj.element-name: paragraph
- obj.language: de
- obj.modality: requirement
- obj.normativity: informative
- obj.specobject-type: provision
- use.business-process: undefined
- use.business-sector: undefined
- use.interaction: undefined
- use.location: undefined
- use.product-category: undefined
- use.product-life-cycle: undefined
- use.project-phase: undefined
- use.purpose: undefined

### prov-7104561-fd59ba3f31de40d: Beurteilung von Gefahren, die von PCB-haltigen Betriebsmitteln ausgehen können, list extract (provision)
Weitere Maßnahmen sind abhängig von dem Ergebnis der Kontaminationsprüfung.
- bib.al.original-language: de
- bib.dp.publication-date: 2018-07-01
- ids.document: 7104561
- ids.tracing: hash-B3D0FB38EAEE5B631D949BA5B6CEB5233285E9689444E24305C08C32ED44F997
- obj.clause-number: Anhang A
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

## R333: Erläuterungen (heading)
- bib.al.original-language: de
- bib.dp.publication-date: 2018-07-01
- ids.document: 7104561
- obj.clause-number: Anhang B
- obj.element-name: heading
- obj.language: de
- obj.specobject-type: heading
- ChapterName: Anhang B Erläuterungen

### prov-7104561-e54ad5fc96cc4ea: Erläuterungen (provision)
– Zu Tabelle 1, PV-Anlagen:
- bib.al.original-language: de
- bib.dp.publication-date: 2018-07-01
- ids.document: 7104561
- ids.tracing: hash-68A587E30D7E40B3C2F99D42C0FBB180C41CA4B04EF3BBA2D4D2DBD8C3393902
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-7104561-732b03c7ffc84bc

### prov-7104561-0675aa2a283f417: Erläuterungen (provision)
Der Aussage, es tritt durch Mondlicht oder künstliches Licht keine elektrische Gefährdung auf, liegen insbesondere die Untersuchungen von Prof. Häberlin und G. Moine, A. M. Serve zugrunde (siehe Literaturhinweise).
- bib.al.original-language: de
- bib.dp.publication-date: 2018-07-01
- ids.document: 7104561
- ids.tracing: hash-9149D98BD0FE0DC7DA67AC9B3B561EBD59C4CE46C5C216043FD03615D384332A
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-7104561-38a58b5a916a4ac: Erläuterungen (provision)
Es treten keine lebensbedrohlichen Ströme auf.
- bib.al.original-language: de
- bib.dp.publication-date: 2018-07-01
- ids.document: 7104561
- ids.tracing: hash-0A5869B156BEFBD74F7231494CF9E95B462ECF46A63753ABDEA2A3775A868167
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-7104561-ea10165d0064427: Erläuterungen (provision)
Eine Körperdurchströmung kann zudem nur auftreten, wenn die Einsatzkraft beide Pole des PV-Generators gleichzeitig berührt.
- bib.al.original-language: de
- bib.dp.publication-date: 2018-07-01
- ids.document: 7104561
- ids.tracing: hash-357002189177EDF63FB5113A64152D30F7A398B9D0EA59A5775E5BACA962AC29
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-7104561-7ec8aedbc99e484: Erläuterungen (provision)
– Zu Tabelle 5:
- bib.al.original-language: de
- bib.dp.publication-date: 2018-07-01
- ids.document: 7104561
- ids.tracing: hash-12644AC6A37EEE5D7ADBD0D8461774DC4D40384DC85616FEA37D522F2055C0D1
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-7104561-69867da9b1324e0

### prov-7104561-3625ec641987412: Erläuterungen (provision)
Die Vergrößerung der Mindestabstände für Strahlrohre DIN 14365-BM wurde der Einfachheit halber geändert.
- bib.al.original-language: de
- bib.dp.publication-date: 2018-07-01
- ids.document: 7104561
- ids.tracing: hash-200F8BD621805268E50F98E8233FC7E933F9EAF90ECC8AAA0D1D8C4D53198C01
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-7104561-073c341f5a154b7: Erläuterungen (provision)
Der Änderung lagen die Angaben der DIN VDE 0132 (VDE 0132):2001-08 zugrunde, wonach sich der Mindestabstand um 0,75 m für jeden Millimeter, um den sich der Mundstück- bzw. der Düsendurchmesser zwischen 12 mm und 22 mm vergrößert, und in Hochspannungsanlagen um zusätzlich 2 m vergrößert.
- bib.al.original-language: de
- bib.dp.publication-date: 2018-07-01
- ids.document: 7104561
- ids.tracing: hash-7EB9A658E1129473F937BF4DE68D42333AE93ACE982A48DF8484222973E57D9C
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> pkn--3014782

### prov-7104561-69f704356f4f421: Erläuterungen (provision)
Geringere Abstände haben bei Einsätzen, in denen Strahlrohre DIN 14365-BM zur Anwendung kommen, praktisch keine Bedeutung.
- bib.al.original-language: de
- bib.dp.publication-date: 2018-07-01
- ids.document: 7104561
- ids.tracing: hash-BF1088BB18DDF79893D334EC00E1DBF43CC20CE5445E25AA78818547B183E9FA
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-7104561-8519a7a795a24bf: Erläuterungen (provision)
– Zur Verwendung von Hohlstrahlrohren nach DIN EN 15182-2:
- bib.al.original-language: de
- bib.dp.publication-date: 2018-07-01
- ids.document: 7104561
- ids.tracing: hash-FF97352793F16C91822B2CCB135C0939CB4B5E17A71B1BA101C280E80A5BD921
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-7104561-3e91be66001144e: Erläuterungen (provision)
Mit Druckluftschaum durchgeführte Versuche der vfdb (Vereinigung zur Förderung des deutschen Brandschutzes e. V.) in Kooperation mit DKE/K 213 haben ergeben, dass eine elektrische Gefährdung in Niederspannungsanlagen aufgrund der Zerfallslänge bei Abgabe über Strahlrohre mit einem maximalen Durchfluss von 235 l/min (siehe DIN EN 15182), die mit einer C-Kupplung nach DIN 14307 angeschlossen werden, nicht auftritt.
- bib.al.original-language: de
- bib.dp.publication-date: 2018-07-01
- ids.document: 7104561
- ids.tracing: hash-4E79416EBF68DB3D4F6558165714EB1F43697B975982B0F1A2578DE3323A0BE1
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-7104561-49cfebb3b1644b3: Erläuterungen (provision)
Daher war es auch konsequent, die Tabelle 5 zur Verwendung mit „C“-Hohlstrahlrohren im Rahmen der Anpassung der Tabelle 6 mit anzupassen.
- bib.al.original-language: de
- bib.dp.publication-date: 2018-07-01
- ids.document: 7104561
- ids.tracing: hash-1770981952485C12F9C006EDE8B1C10298BDEF1049F8B44272D4F22A37F5E674
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-7104561-69867da9b1324e0
- cross-reference -> prov-7104561-286c2354700d493

### prov-7104561-892c2eebed0d4ca: Erläuterungen (provision)
Gleichwohl wird aufgrund arbeitsschutzrechtlicher Anforderungen empfohlen, anstelle einer einzelfallbezogenen Gefährdungsbeurteilung zur Eignung der Strahlrohre durch den Unternehmer (hier: Feuerwehr) die elektrische Gefährdung im Vorfeld durch die Strahlrohrhersteller zu überprüfen (z. B. durch Messungen analog DIN 14365).
- bib.al.original-language: de
- bib.dp.publication-date: 2018-07-01
- ids.document: 7104561
- ids.tracing: hash-4773C3F8ABBCF3E78025019873B9C8D4247F68628805DDA347A14C869C9BFE38
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-7104561-8b606c1931284d1: Erläuterungen (provision)
– Zu Tabelle 6, Zur Verwendung von Schaum in Hochspannungsanlagen:
- bib.al.original-language: de
- bib.dp.publication-date: 2018-07-01
- ids.document: 7104561
- ids.tracing: hash-B47BC44BD2B832094CF5AAE5B10732A2BD5364C0A735A156E0BCCABE0741A725
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined
- cross-reference -> prov-7104561-286c2354700d493

### prov-7104561-da358d75db0c47a: Erläuterungen (provision)
Durch Schaum werden die Isolationsstrecken beeinträchtigt.
- bib.al.original-language: de
- bib.dp.publication-date: 2018-07-01
- ids.document: 7104561
- ids.tracing: hash-8A02DF3D9CA9CDC327A3476327D270C2359E2417F26C58F18391B636D4F36AA0
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

### prov-7104561-2f58d25344064d8: Erläuterungen (provision)
Dies kann zu Erd- und Kurzschlüssen führen, einhergehend mit explosionsartigen Zerstörungen der elektrischen Anlagen.
- bib.al.original-language: de
- bib.dp.publication-date: 2018-07-01
- ids.document: 7104561
- ids.tracing: hash-0167A7DC5700E41A81303B25FA34A083CDA71031BD15DBD8E4C03CEF75367888
- obj.clause-number: Anhang B
- obj.element-name: paragraph
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

## R349: Literaturhinweise (heading)
- bib.al.original-language: de
- bib.dp.publication-date: 2018-07-01
- ids.document: 7104561
- obj.element-name: heading
- obj.language: de
- obj.specobject-type: heading

### prov-7104561-d6c9cb8546c84cc: Literaturhinweise (provision)
- Verordnung über Sicherheits- und Gesundheitsschutz bei der Bereitstellung von Arbeitsmitteln und deren Benutzung bei der Arbeit, über Sicherheit beim Betrieb überwachungsbedürftiger Anlagen und über die Organisation des betrieblichen Arbeitsschutzes (Betriebssicherheitsverordnung – BetrSichV)
- DGUV Information 204-006 (BGI/GUV-I 503):2011, Information – Anleitung zur Ersten Hilfe
- DGUV Information 203-052 (BGI/GUV-I 8677):2011, Information – Elektrische Gefahren an der Einsatzstelle – Vortrag für Einsatzkräfte
- DGUV Information 200-005 (BGI/GUV-I 8686):2012, Information – Qualifizierung für Arbeiten an Fahrzeugen mit Hochvoltsystemen
- DGUV Vorschrift 1 (BGV A1) (GUV-V A1):2013, Unfallverhütungsvorschrift – Grundsätze der Prävention
- GUV-V C53 (DGUV Vorschrift 49):2005, Unfallverhütungsvorschrift „Feuerwehren“ mit Durchführungsanweisungen
- Verordnung zum Schutz vor Gefahrstoffen (Gefahrstoffverordnung – GefStoffV)
- Häberlin, H., Borgna, L., Schärf, P., PV und Feuerwehr: Keine Panik, realistische Einschätzung der elektrischen Gefahren und möglicher Gegenmaßnahmen, 26. Symposium Photovoltaische Solarenergie Staffelstein, 2011
- Moine, G., Serve, A. M., Campagne de tests Nocturnes sur la Plateforme Photovoltaique Qualiphoton de Transenergie, veröffentlicht durch Direction de la Sécurité Civile (DSC), Syndicat des Energies Renouvables, Transenergie
- bib.al.original-language: de
- bib.dp.publication-date: 2018-07-01
- ids.document: 7104561
- ids.tracing: hash-D11DEEF4D8D4B8E6BB45D60ABF305C8A542CFCC3B74DD77D9891959B8E9F50C4
- obj.element-name: list-of-documents
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

#### prov-7104561-fc5e7e43be4f445: Literaturhinweise, list extract (provision)
- Verordnung über Sicherheits- und Gesundheitsschutz bei der Bereitstellung von Arbeitsmitteln und deren Benutzung bei der Arbeit, über Sicherheit beim Betrieb überwachungsbedürftiger Anlagen und über die Organisation des betrieblichen Arbeitsschutzes (Betriebssicherheitsverordnung – BetrSichV)
- DGUV Information 204-006 (BGI/GUV-I 503):2011, Information – Anleitung zur Ersten Hilfe
- DGUV Information 203-052 (BGI/GUV-I 8677):2011, Information – Elektrische Gefahren an der Einsatzstelle – Vortrag für Einsatzkräfte
- DGUV Information 200-005 (BGI/GUV-I 8686):2012, Information – Qualifizierung für Arbeiten an Fahrzeugen mit Hochvoltsystemen
- DGUV Vorschrift 1 (BGV A1) (GUV-V A1):2013, Unfallverhütungsvorschrift – Grundsätze der Prävention
- GUV-V C53 (DGUV Vorschrift 49):2005, Unfallverhütungsvorschrift „Feuerwehren“ mit Durchführungsanweisungen
- Verordnung zum Schutz vor Gefahrstoffen (Gefahrstoffverordnung – GefStoffV)
- Häberlin, H., Borgna, L., Schärf, P., PV und Feuerwehr: Keine Panik, realistische Einschätzung der elektrischen Gefahren und möglicher Gegenmaßnahmen, 26. Symposium Photovoltaische Solarenergie Staffelstein, 2011
- Moine, G., Serve, A. M., Campagne de tests Nocturnes sur la Plateforme Photovoltaique Qualiphoton de Transenergie, veröffentlicht durch Direction de la Sécurité Civile (DSC), Syndicat des Energies Renouvables, Transenergie
- bib.al.original-language: de
- bib.dp.publication-date: 2018-07-01
- ids.document: 7104561
- ids.tracing: hash-CE634140949DFC2C413B1F59F7E86F1F16E8667853E386EAFDC37613FF651BD4
- obj.element-name: list-of-documents
- obj.language: de
- obj.modality: undefined
- obj.normativity: informative
- obj.specobject-type: provision
- use.business-process: undefined
- use.business-sector: undefined
- use.interaction: undefined
- use.location: undefined
- use.product-category: undefined
- use.product-life-cycle: undefined
- use.project-phase: undefined
- use.purpose: undefined

# Specification: Referenced documents

## pkn--7061874 (document)
DIN VDE 0132 (VDE 0132):2015-10
- ids.document: 7061874
- obj.language: de
- obj.specobject-type: document
- pub.software: VDE CaaS 1.5.15
- pub.supplier: VDE
- pub.transformation-date: 2025-06-23T14:21:16.107673548Z
- pub.url: https://[changeme].dke.de/api/publications/7061874/reqif

## pkn--7095271 (document)
DIN EN 50122-1 (VDE 0115-3):2017-10
- ids.document: 7095271
- obj.language: de
- obj.specobject-type: document
- pub.software: VDE CaaS 1.5.15
- pub.supplier: VDE
- pub.transformation-date: 2025-06-23T14:21:16.107673548Z
- pub.url: https://[changeme].dke.de/api/publications/7095271/reqif

## pkn--7036174 (document)
DIN EN 62040-1 (VDE 0558-510):2013-11
- ids.document: 7036174
- obj.language: de
- obj.specobject-type: document
- pub.software: VDE CaaS 1.5.15
- pub.supplier: VDE
- pub.transformation-date: 2025-06-23T14:21:16.107673548Z
- pub.url: https://[changeme].dke.de/api/publications/7036174/reqif

## pkn (document)
- obj.language: de
- obj.specobject-type: document
- pub.software: VDE CaaS 1.5.15
- pub.supplier: VDE
- pub.transformation-date: 2025-06-23T14:21:16.107673548Z
- pub.url: https://[changeme].dke.de/api/publications//reqif

## pkn--7048005 (document)
DIN VDE 0105-103 (VDE 0105-103):2014-10
- ids.document: 7048005
- obj.language: de
- obj.specobject-type: document
- pub.software: VDE CaaS 1.5.15
- pub.supplier: VDE
- pub.transformation-date: 2025-06-23T14:21:16.107673548Z
- pub.url: https://[changeme].dke.de/api/publications/7048005/reqif

## pkn--4020860 (document)
E DIN IEC 62335 (VDE 0661-20):2008-08
- ids.document: 4020860
- obj.language: de
- obj.specobject-type: document
- pub.software: VDE CaaS 1.5.15
- pub.supplier: VDE
- pub.transformation-date: 2025-06-23T14:21:16.107673548Z
- pub.url: https://[changeme].dke.de/api/publications/4020860/reqif

## pkn--3020662 (document)
DIN EN 62040-1 (VDE 0558-510):2009-06
- ids.document: 3020662
- obj.language: de
- obj.specobject-type: document
- pub.software: VDE CaaS 1.5.15
- pub.supplier: VDE
- pub.transformation-date: 2025-06-23T14:21:16.107673548Z
- pub.url: https://[changeme].dke.de/api/publications/3020662/reqif

## pkn--3011489 (document)
DIN VDE 0105-100 (VDE 0105-100):1997-10
- ids.document: 3011489
- obj.language: de
- obj.specobject-type: document
- pub.software: VDE CaaS 1.5.15
- pub.supplier: VDE
- pub.transformation-date: 2025-06-23T14:21:16.107673548Z
- pub.url: https://[changeme].dke.de/api/publications/3011489/reqif

## pkn--3014782 (document)
DIN VDE 0132 (VDE 0132):2001-08
- ids.document: 3014782
- obj.language: de
- obj.specobject-type: document
- pub.software: VDE CaaS 1.5.15
- pub.supplier: VDE
- pub.transformation-date: 2025-06-23T14:21:16.107673548Z
- pub.url: https://[changeme].dke.de/api/publications/3014782/reqif
